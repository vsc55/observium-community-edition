NMS-GPON-MIB  DEFINITIONS ::= BEGIN

    IMPORTS
        MODULE-IDENTITY,
        OBJECT-TYPE,BITS, Counter64
            FROM SNMPv2-SMI
        
        DisplayString,ifIndex,ifDescr,PhysAddress
            FROM RFC1213-MIB
        nms
            FROM NMS-SMI 
        PhysAddress, RowStatus, DateAndTime, TruthValue, MacAddress
            FROM SNMPv2-TC
        InetAddressIPv6
            FROM INET-ADDRESS-MIB;
            
            

                        
nmsGponMIB  MODULE-IDENTITY
        LAST-UPDATED    "201511300000Z"
        ORGANIZATION    ""
        CONTACT-INFO
                    ""
            
        DESCRIPTION
                "nmsGponProfile management group."
        ::= { nms 10 }

--nmsGponOltObj OLT任务 OID:1.3.6.1.4.1.3320.10.1
        
nmsGponOltObj   OBJECT IDENTIFIER ::= { nmsGponMIB 1 }  
        
-- 全局配置表

gponOltConfigTable   OBJECT IDENTIFIER ::= { nmsGponOltObj 1 }  

gponOltConfigEntry   OBJECT IDENTIFIER ::= { gponOltConfigTable 1 }  
               
                 
          gponOnuAuthenticationMode OBJECT-TYPE
              SYNTAX  INTEGER{
                        disable(0),
                        serial_number_only(1),
                        password_only(2),
                        serial_number_and_password(3),
                        loid(4),
                        hybrid(5)
                             }
              ACCESS  read-write
              STATUS  mandatory
              DESCRIPTION
                      "Authentication method:
                        0 Disabled, so all ONU/ONTs are allowed to be activated always, When this option is selected;
                        1 Serial number only;
                        2 password_only;
                        3 Serial number and password;
                        4 LOID
                        5 Hybrid, so ONU/ONTs are allowed to be activated, if SN-only or LOID Authentication have been passed.
                        Default value is 0."
              ::= { gponOltConfigEntry 1 }
                 
          gponBroadcastGEMPort OBJECT-TYPE
              SYNTAX  INTEGER
              ACCESS  read-write
              STATUS  mandatory
              DESCRIPTION
                      "GEM port for incidental broadcast traffic. Set to 0, if no dedicated GEM port is needed for broadcast
                       traffic and broadcast traffic will be sent on unicast GEM ports."
              ::= { gponOltConfigEntry 2 }
                 
          gponEncryption OBJECT-TYPE
              SYNTAX  INTEGER{
                        disable(0),
                        enable(1)
                             }
              ACCESS  read-write
              STATUS  mandatory
              DESCRIPTION
                      "GPON encryption switch.1-Enable  0-Disable. Default value is 0."
              ::= { gponOltConfigEntry 3 }
                 
          gponKeyExchangeInterval OBJECT-TYPE
              SYNTAX  INTEGER(1..3600)
              ACCESS  read-write
              STATUS  mandatory
              DESCRIPTION
                      "Key exchange interval in milliseconds.1-3600. Default value is 3600."
              ::= { gponOltConfigEntry 4 }
                 
          gponOnuUniLinkStatusOn OBJECT-TYPE
              SYNTAX  INTEGER{
                        enable(1),
                        disable(2)
                             }
              ACCESS  read-write
              STATUS  mandatory
              DESCRIPTION
                      "Onu uni port link status notify enable or disable.1-enable,2-disable."
              ::= { gponOltConfigEntry 5 }

          gponVirtualportScheduler OBJECT-TYPE
              SYNTAX  INTEGER{
                        processing(0),
                        disable(1),
                        base-vp(2),
                        base-onu(3)
                             }
              ACCESS  read-write
              STATUS  mandatory
              DESCRIPTION
                      "Onu port egress flow scheduler mode. 0-processing,1-disable,2-base-vp,3-base-onu"
              ::= { gponOltConfigEntry 6 }  
              
          gponLoidOverwriteStaticSN OBJECT-TYPE
              SYNTAX  INTEGER{
                        disable(0),
                        enale(1)
                             }
              ACCESS  read-write
              STATUS  mandatory
              DESCRIPTION
                      "Config loid Overwrite Static SN.1-enable,0-disable."
              ::= { gponOltConfigEntry 7 }
          
          gponPasswordOverwriteStaticSN OBJECT-TYPE
              SYNTAX  INTEGER{
                        disable(0),
                        enable(1)
                             }
              ACCESS  read-write
              STATUS  mandatory
              DESCRIPTION
                      "Config password Overwrite Static SN.1-enable,0-disable."
              ::= { gponOltConfigEntry 8 }

          gponOnuOmciMibResetOnActive OBJECT-TYPE
              SYNTAX  INTEGER{
                        enable(1),
                        disable(2)
                             }
              ACCESS  read-write
              STATUS  mandatory
              DESCRIPTION
                      "Enable/Disable onu omci mib-reset on onu active.1-enable,2-disable."
              ::= { gponOltConfigEntry 9 }

          gponOnuOmciKeepAlive OBJECT-TYPE
              SYNTAX  INTEGER{
                        enable(1),
                        disable(2)
                             }
              ACCESS  read-write
              STATUS  mandatory
              DESCRIPTION
                      "Enable/Disable onu omci keep-alive.1-enable,2-disable."
              ::= { gponOltConfigEntry 10 }

          gponOnuOmciMibAudit OBJECT-TYPE
              SYNTAX  INTEGER{
                        enable(1),
                        disable(2)
                             }
              ACCESS  read-write
              STATUS  mandatory
              DESCRIPTION
                      "Enable/Disable onu omci mib-audit.1-enable,2-disable."
              ::= { gponOltConfigEntry 11 }

          gponOnuOmciAlarmAudit OBJECT-TYPE
              SYNTAX  INTEGER{
                        enable(1),
                        disable(2)
                             }
              ACCESS  read-write
              STATUS  mandatory
              DESCRIPTION
                      "Enable/Disable onu omci alarm-audit.1-enable,2-disable."
              ::= { gponOltConfigEntry 12 }

          gponOnuSNFormatType OBJECT-TYPE
              SYNTAX  INTEGER{
                        type-1(1),
                        type-2(2)
                             }
              ACCESS  read-write
              STATUS  mandatory
              DESCRIPTION
                      "ONU serial number display format.
                      Type-1 - XXXX:XXXXXXXX(First 4 bytes of vendor id as character display.
                      Type-2 - XXXXXXXXXXXXXXXX(All 8 bytes as hex data display)
                      "
              ::= { gponOltConfigEntry 13 }

-- 地理信息配置              
gponOltPosition         OBJECT IDENTIFIER ::= { nmsGponOltObj 2 }
       gponOltPositionLongitude OBJECT-TYPE
           SYNTAX  INTEGER(-18000000..18000000)
           ACCESS  read-write
           STATUS  mandatory
           DESCRIPTION
                   "Set operation will only prepare configuration buffer, and will not take effect before gponOltPositionAction is set."
           ::= { gponOltPosition 1 } 
       
       
       gponOltPositionLatitude OBJECT-TYPE
           SYNTAX  INTEGER(-9000000..9000000)
           ACCESS  read-write
           STATUS  mandatory
           DESCRIPTION
                   "Set operation will only prepare configuration buffer, and will not take effect before gponOltPositionAction is set."
           ::= { gponOltPosition 2 } 
           
           
       gponOltPositionElevation OBJECT-TYPE
           SYNTAX  INTEGER(-10000..10000)
           ACCESS  read-write
           STATUS  mandatory
           DESCRIPTION
                   "Set operation will only prepare configuration buffer, and will not take effect before gponOltPositionAction is set."
           ::= { gponOltPosition 3 } 
           
           
           
       gponOltPositionHorizonalerr OBJECT-TYPE
           SYNTAX  INTEGER(0..50000)
           ACCESS  read-write
           STATUS  mandatory
           DESCRIPTION
                   "Set operation will only prepare configuration buffer, and will not take effect before gponOltPositionAction is set."
           ::= { gponOltPosition 4 } 
           
           
       gponOltPositionAltitudeerr OBJECT-TYPE
           SYNTAX  INTEGER(0..50000)
           ACCESS  read-write
           STATUS  mandatory
           DESCRIPTION
                   "Set operation will only prepare configuration buffer, and will not take effect before gponOltPositionAction is set."
           ::= { gponOltPosition 5 } 
           
           
       gponOltPositionAreacode OBJECT-TYPE
           SYNTAX  OCTET STRING (SIZE (0..18))
           ACCESS  read-write
           STATUS  mandatory
           DESCRIPTION
                   "Set operation will only prepare configuration buffer, and will not take effect before gponOltPositionAction is set."
           ::= { gponOltPosition 6 } 
           
           
       gponOltPositionTimestamp OBJECT-TYPE
           SYNTAX  INTEGER
           ACCESS  read-write
           STATUS  mandatory
           DESCRIPTION
                   "Set operation will only prepare configuration buffer, and will not take effect before gponOltPositionAction is set."
           ::= { gponOltPosition 7 } 
           
           
       gponOltPositionGISDigest OBJECT-TYPE
           SYNTAX  OCTET STRING (SIZE (0..18))
           ACCESS  read-write
           STATUS  mandatory
           DESCRIPTION
                   "Set operation will only prepare configuration buffer, and will not take effect before gponOltPositionAction is set."
           ::= { gponOltPosition 8 } 
           
           
       gponOltPositionGISCheck OBJECT-TYPE
           SYNTAX  OCTET STRING (SIZE (4..6))
           ACCESS  read-write
           STATUS  mandatory
           DESCRIPTION
                   "Set operation will only prepare configuration buffer, and will not take effect before gponOltPositionAction is set."
           ::= { gponOltPosition 9 } 
           
           
       gponOltPositionAction OBJECT-TYPE
           SYNTAX  INTEGER{no_action(0),
                           apply(1)
                           }
           ACCESS  write-only
           STATUS  mandatory
           DESCRIPTION
                   "While set to 1, all the configuration in buffer will apply to device and the configuration works."
           ::= { gponOltPosition 10 } 
           
           
       gponOltPositionResult OBJECT-TYPE
           SYNTAX  INTEGER{success(0),
                           failed(1),
                           unknow(2)
                           }
           ACCESS  read-only
           STATUS  mandatory
           DESCRIPTION
                   "Position configuraton applying result."
           ::= { gponOltPosition 11 } 


--nmsGponOltPonPortObj PON端口任务 OID:1.3.6.1.4.1.3320.10.2

--PON端口配置表

nmsGponOltPonPortObj  OBJECT IDENTIFIER ::= { nmsGponMIB 2 }  

             gponOltPonPortConfigTable OBJECT-TYPE
                 SYNTAX  SEQUENCE OF GponOltPonPortConfigEntry
                 ACCESS  not-accessible
                 STATUS  mandatory
                 DESCRIPTION
                          "gpon Olt Pon Port Config table."
                 ::= { nmsGponOltPonPortObj 1 }

             gponOltPonPortConfigEntry OBJECT-TYPE
                 SYNTAX GponOltPonPortConfigEntry
                 ACCESS  not-accessible
                 STATUS  mandatory
                 DESCRIPTION
                          "gpon Olt Pon Port Config ."
                 INDEX { gponOltPonPortPortIndex }
             ::= { gponOltPonPortConfigTable 1 }

             GponOltPonPortConfigEntry ::=
                 SEQUENCE {
                     gponOltPonPortPortIndex
                         INTEGER,
                     gponOltPonPortPortAdminStatus
                         INTEGER,
                     gponOltPonPortOnuDiscoveryMode 
                         INTEGER,
                     gponOltPonPortPortActiveOnuNum
                         INTEGER,   
                     gponOltPonPortPortInactiveOnuNum 
                         INTEGER,
                     gponOltPonPortPortLlidIfIndexString
                         OCTET STRING,
                     gponOltPonPortPortFEC
                         INTEGER,
                     gponOltPonPortOnuAuthenticationMethod
                         INTEGER,
                     gponOltPonPortIngressQosMode
                         INTEGER,
                     gponOltPonPortEgressQosMode
                         INTEGER
                 }
                 
                 
          gponOltPonPortPortIndex OBJECT-TYPE
              SYNTAX  INTEGER
              ACCESS  read-only
              STATUS  mandatory

              DESCRIPTION
                      "Index of the table, PON port INDEX."
              ::= { gponOltPonPortConfigEntry 1 }

          gponOltPonPortPortAdminStatus OBJECT-TYPE
              SYNTAX  INTEGER{
                           no-shutdown(1),
                           shutdown(2)
                              }
              ACCESS  read-write
              STATUS  mandatory

              DESCRIPTION
                      "1-No shutdown 2-shutdown."
              ::= { gponOltPonPortConfigEntry 2 }

          gponOltPonPortOnuDiscoveryMode OBJECT-TYPE
              SYNTAX  INTEGER{
                           auto(1),
                           manual(2),
                           disable(3)
                              }
              ACCESS  read-write
              STATUS  mandatory

              DESCRIPTION
                      "ONU discovery mode: 1 Auto periodic (onuDiscoveryInterval is the period),2 Manual enabled once
                       then disabled, 3 Disabled,  "
              ::= { gponOltPonPortConfigEntry 3 }

          gponOltPonPortPortActiveOnuNum OBJECT-TYPE
              SYNTAX  INTEGER
              ACCESS  read-only
              STATUS  mandatory

              DESCRIPTION
                      "ONU count of this pon port which is in active status ."
              ::= { gponOltPonPortConfigEntry 4 }

          gponOltPonPortPortInactiveOnuNum OBJECT-TYPE
              SYNTAX  INTEGER
              ACCESS  read-only
              STATUS  mandatory

              DESCRIPTION
                      "ONU count of this pon port which is in inactive status ."
              ::= { gponOltPonPortConfigEntry 5 }

          gponOltPonPortPortLlidIfIndexString OBJECT-TYPE
              SYNTAX  OCTET STRING
              ACCESS  read-only
              STATUS  mandatory

              DESCRIPTION
                      "For diID of this PON port is 32, 33, 34. This string should be writed as '32,33,34'. "
              ::= { gponOltPonPortConfigEntry 6 }
          
          gponOltPonPortPortFEC OBJECT-TYPE
              SYNTAX  INTEGER{
                           enable(1),
                           disable(2)
                              }
              ACCESS  read-write
              STATUS  mandatory

              DESCRIPTION
                      "For PON port FEC config. "
              ::= { gponOltPonPortConfigEntry 7 }

          gponOltPonPortOnuAuthenticationMethod OBJECT-TYPE
              SYNTAX  INTEGER{
                    disable(0),
                    serial_number_only(1),
                    password_only(2),
                    serial_number_and_password(3),
                    loid(4),
                    hybrid(5)
                }
              ACCESS  read-write
              STATUS  mandatory
              DESCRIPTION
                      "Authentication method:
                        0 Disabled, so all ONU/ONTs are allowed to be activated always, When this option is selected;
                        1 Serial number only;
                        2 password_only;
                        3 Serial number and password;
                        4 LOID
                        5 Hybrid, so ONU/ONTs are allowed to be activated, if SN-only or LOID Authentication have been passed.
                        Default value is 0."
              ::= { gponOltPonPortConfigEntry 8 }

          gponOltPonPortIngressQosMode OBJECT-TYPE
              SYNTAX  INTEGER{
                    pon_port(0),
                    virtualport(1)
                }
              ACCESS  read-write
              STATUS  mandatory
              DESCRIPTION
                      "Qos mode ingress:
                        0 ingress QoS mode pon;
                        1 ingress QoS mode virtualport."
              ::= { gponOltPonPortConfigEntry 9 }

          gponOltPonPortEgressQosMode OBJECT-TYPE
              SYNTAX  INTEGER{
                    pon_port(0),
                    virtualport(1)
                }
              ACCESS  read-write
              STATUS  mandatory
              DESCRIPTION
                      "Qos mode egress:
                        0 egress QoS mode pon;
                        1 egress QoS mode virtualport."
              ::= { gponOltPonPortConfigEntry 10 }

--OLT PON端口光功率

             gponOltPonPortOpticalParameterTable OBJECT-TYPE
                 SYNTAX  SEQUENCE OF GponOltPonPortOpticalParameterEntry
                 ACCESS  not-accessible
                 STATUS  mandatory
                 DESCRIPTION
                          "gpon Olt Pon Port Config table."
                 ::= { nmsGponOltPonPortObj 2 }

             gponOltPonPortOpticalParameterEntry OBJECT-TYPE
                 SYNTAX GponOltPonPortOpticalParameterEntry
                 ACCESS  not-accessible
                 STATUS  mandatory
                 DESCRIPTION
                          "gpon Olt Pon Port Config ."
                 INDEX { gponOltPonPortOpticalParameterPortIndex }
             ::= { gponOltPonPortOpticalParameterTable 1 }

             GponOltPonPortOpticalParameterEntry ::=
                 SEQUENCE {
                     gponOltPonPortOpticalParameterPortIndex
                         INTEGER,
                     gponOltPonPortOpticalParameterTemperature
                         INTEGER,
                     gponOltPonPortOpticalParameterVoltage 
                         INTEGER,
                     gponOltPonPortOpticalParameterCurrent
                         INTEGER,   
                     gponOltPonPortOpticalParameterTxPower 
                         INTEGER
                 }
                 
                 
          gponOltPonPortOpticalParameterPortIndex OBJECT-TYPE
              SYNTAX  INTEGER
              ACCESS  read-only
              STATUS  mandatory

              DESCRIPTION
                      "Index of the table, PON port INDEX."
              ::= { gponOltPonPortOpticalParameterEntry 1 }

          gponOltPonPortOpticalParameterTemperature OBJECT-TYPE
              SYNTAX  INTEGER
              ACCESS  read-only
              STATUS  mandatory

              DESCRIPTION
                      ""
              ::= { gponOltPonPortOpticalParameterEntry 2 }

          gponOltPonPortOpticalParameterVoltage OBJECT-TYPE
              SYNTAX  INTEGER
              ACCESS  read-only
              STATUS  mandatory

              DESCRIPTION
                      ""
              ::= { gponOltPonPortOpticalParameterEntry 3 }

          gponOltPonPortOpticalParameterCurrent OBJECT-TYPE
              SYNTAX  INTEGER
              ACCESS  read-only
              STATUS  mandatory

              DESCRIPTION
                      ""
              ::= { gponOltPonPortOpticalParameterEntry 4 }

          gponOltPonPortOpticalParameterTxPower OBJECT-TYPE
              SYNTAX  INTEGER
              ACCESS  read-only
              STATUS  mandatory

              DESCRIPTION
                      ""
              ::= { gponOltPonPortOpticalParameterEntry 5 }

--OLT PON端口接收光功率

             gponOltPonPortOpticalRxPowerTable OBJECT-TYPE
                 SYNTAX  SEQUENCE OF GponOltPonPortOpticalRxPowerEntry
                 ACCESS  not-accessible
                 STATUS  mandatory
                 DESCRIPTION
                          "gpon Olt Pon Port Config table."
                 ::= { nmsGponOltPonPortObj 3 }

             gponOltPonPortOpticalRxPowerEntry OBJECT-TYPE
                 SYNTAX GponOltPonPortOpticalRxPowerEntry
                 ACCESS  not-accessible
                 STATUS  mandatory
                 DESCRIPTION
                          "gpon Olt Pon Port Config ."
                 INDEX { gponOltPonPortOpticalRxPowerPortIndex }
             ::= { gponOltPonPortOpticalRxPowerTable 1 }

             GponOltPonPortOpticalRxPowerEntry ::=
                 SEQUENCE {
                     gponOltPonPortOpticalRxPowerPortIndex
                         INTEGER,
                     gponOltPonPortOpticalRxPowerLinkStatus
                         INTEGER,
                     gponOltPonPortOpticalRxPowerRxPower 
                         INTEGER
                 }
                 
                 
          gponOltPonPortOpticalRxPowerPortIndex OBJECT-TYPE
              SYNTAX  INTEGER
              ACCESS  read-only
              STATUS  mandatory

              DESCRIPTION
                      "Index of the table, PON port INDEX."
              ::= { gponOltPonPortOpticalRxPowerEntry 1 }

          gponOltPonPortOpticalRxPowerLinkStatus OBJECT-TYPE
              SYNTAX  INTEGER{
                               link-up(1),
                               link-down(2)
                              }
              ACCESS  read-only
              STATUS  mandatory

              DESCRIPTION
                      ""
              ::= { gponOltPonPortOpticalRxPowerEntry 2 }

          gponOltPonPortOpticalRxPowerRxPower OBJECT-TYPE
              SYNTAX  INTEGER
              ACCESS  read-only
              STATUS  mandatory

              DESCRIPTION
                      "The rx power of optical module. The unit is 0.1DBm."
              ::= { gponOltPonPortOpticalRxPowerEntry 3 }


--OLT PON端口光功率告警

             gponOltPonPortOpticalParameterAlarmTable OBJECT-TYPE
                 SYNTAX  SEQUENCE OF GponOltPonPortOpticalParameterAlarmEntry
                 ACCESS  not-accessible
                 STATUS  mandatory
                 DESCRIPTION
                          "gpon Olt Pon Port Config table."
                 ::= { nmsGponOltPonPortObj 4 }

             gponOltPonPortOpticalParameterAlarmEntry OBJECT-TYPE
                 SYNTAX GponOltPonPortOpticalParameterAlarmEntry
                 ACCESS  not-accessible
                 STATUS  mandatory
                 DESCRIPTION
                          "gpon Olt Pon Port Config ."
                 INDEX { gponOltPonPortPowerAlarmIndex }
             ::= { gponOltPonPortOpticalParameterAlarmTable 1 }

             GponOltPonPortOpticalParameterAlarmEntry ::=
                 SEQUENCE {
                     gponOltPonPortPowerAlarmIndex
                         INTEGER,
                     gponOltPonPortTxPowerAlarmUpLimitEnable
                         INTEGER,
                     gponOltPonPortTxPowerAlarmUpLimitThreshold 
                         INTEGER,
                     gponOltPonPortTxPowerAlarmUpLimitClearThreshold
                         INTEGER,
                     gponOltPonPortTxPowerAlarmLowLimitEnable
                         INTEGER,
                     gponOltPonPortTxPowerAlarmLowLimitThreshold 
                         INTEGER,
                     gponOltPonPortTxPowerAlarmLowLimitClearThreshold
                         INTEGER,
                     gponOltPonPortTemperatureAlarmUpLimitEnable
                         INTEGER,
                     gponOltPonPortTemperatureAlarmUpLimitThreshold 
                         INTEGER,
                     gponOltPonPortTemperatureAlarmUpLimitClearThreshold
                         INTEGER,
                     gponOltPonPortTemperatureAlarmLowLimitEnable
                         INTEGER,
                     gponOltPonPortTemperatureAlarmLowLimitThreshold 
                         INTEGER,
                     gponOltPonPortTemperatureAlarmLowLimitClearThreshold
                         INTEGER,
                     gponOltPonPortVoltageAlarmUpLimitEnable
                         INTEGER,    
                     gponOltPonPortVoltageAlarmUpLimitThreshold 
                         INTEGER,
                     gponOltPonPortTxPowerAlarmUpLimitThreshold 
                         INTEGER,
                     gponOltPonPortVoltageAlarmUpLimitClearThreshold
                         INTEGER,
                     gponOltPonPortVoltageAlarmLowLimitEnable
                         INTEGER,
                     gponOltPonPortVoltageAlarmLowLimitThreshold 
                         INTEGER,
                     gponOltPonPortVoltageAlarmLowLimitClearThreshold
                         INTEGER,
                     gponOltPonPortCurrentAlarmUpLimitEnable
                         INTEGER,
                     gponOltPonPortCurrentAlarmUpLimitThreshold 
                         INTEGER,
                     gponOltPonPortCurrentAlarmUpLimitClearThreshold
                         INTEGER,
                     gponOltPonPortCurrentAlarmLowLimitEnable
                         INTEGER,
                     gponOltPonPortCurrentAlarmLowLimitThreshold 
                         INTEGER,
                     gponOltPonPortCurrentAlarmLowLimitClearThreshold 
                         INTEGER
                 }
                                 
          gponOltPonPortPowerAlarmIndex OBJECT-TYPE
              SYNTAX  INTEGER
              ACCESS  read-only
              STATUS  mandatory
              DESCRIPTION
                      "Index of the table, PON port INDEX."
              ::= { gponOltPonPortOpticalParameterAlarmEntry 1 }

          gponOltPonPortTxPowerAlarmUpLimitEnable OBJECT-TYPE
              SYNTAX  INTEGER{
                              enable(1),
                              disable(2)
                             }
              ACCESS  read-write
              STATUS  mandatory
              DESCRIPTION
                      "Index of the table, PON port INDEX."
              ::= { gponOltPonPortOpticalParameterAlarmEntry 2 }

          gponOltPonPortTxPowerAlarmUpLimitThreshold OBJECT-TYPE
              SYNTAX  INTEGER
              ACCESS  read-write
              STATUS  mandatory
              DESCRIPTION
                      ""
              ::= { gponOltPonPortOpticalParameterAlarmEntry 3 }

          gponOltPonPortTxPowerAlarmUpLimitClearThreshold OBJECT-TYPE
              SYNTAX  INTEGER
              ACCESS  read-write
              STATUS  mandatory
              DESCRIPTION
                      ""
              ::= { gponOltPonPortOpticalParameterAlarmEntry 4 }

          gponOltPonPortTxPowerAlarmLowLimitEnable OBJECT-TYPE
              SYNTAX  INTEGER{
                              enable(1),
                              disable(2)
                             }
              ACCESS  read-write
              STATUS  mandatory
              DESCRIPTION
                      "Index of the table, PON port INDEX."
              ::= { gponOltPonPortOpticalParameterAlarmEntry 5 }

          gponOltPonPortTxPowerAlarmLowLimitThreshold OBJECT-TYPE
              SYNTAX  INTEGER
              ACCESS  read-write
              STATUS  mandatory
              DESCRIPTION
                      ""
              ::= { gponOltPonPortOpticalParameterAlarmEntry 6 }

          gponOltPonPortTxPowerAlarmLowLimitClearThreshold OBJECT-TYPE
              SYNTAX  INTEGER
              ACCESS  read-write
              STATUS  mandatory
              DESCRIPTION
                      ""
              ::= { gponOltPonPortOpticalParameterAlarmEntry 7 }

          gponOltPonPortTemperatureAlarmUpLimitEnable OBJECT-TYPE
              SYNTAX  INTEGER{
                              enable(1),
                              disable(2)
                             }
              ACCESS  read-write
              STATUS  mandatory
              DESCRIPTION
                      ""
              ::= { gponOltPonPortOpticalParameterAlarmEntry 8 }

          gponOltPonPortTemperatureAlarmUpLimitThreshold OBJECT-TYPE
              SYNTAX  INTEGER
              ACCESS  read-write
              STATUS  mandatory
              DESCRIPTION
                      ""
              ::= { gponOltPonPortOpticalParameterAlarmEntry 9 }

          gponOltPonPortTemperatureAlarmUpLimitClearThreshold OBJECT-TYPE
              SYNTAX  INTEGER
              ACCESS  read-write
              STATUS  mandatory
              DESCRIPTION
                      ""
              ::= { gponOltPonPortOpticalParameterAlarmEntry 10 }

          gponOltPonPortTemperatureAlarmLowLimitEnable OBJECT-TYPE
              SYNTAX  INTEGER{
                              enable(1),
                              disable(2)
                             }
              ACCESS  read-write
              STATUS  mandatory
              DESCRIPTION
                      ""
              ::= { gponOltPonPortOpticalParameterAlarmEntry 11 }

          gponOltPonPortTemperatureAlarmLowLimitThreshold OBJECT-TYPE
              SYNTAX  INTEGER
              ACCESS  read-write
              STATUS  mandatory
              DESCRIPTION
                      ""
              ::= { gponOltPonPortOpticalParameterAlarmEntry 12 }

          gponOltPonPortTemperatureAlarmLowLimitClearThreshold OBJECT-TYPE
              SYNTAX  INTEGER
              ACCESS  read-write
              STATUS  mandatory
              DESCRIPTION
                      ""
              ::= { gponOltPonPortOpticalParameterAlarmEntry 13 }

          gponOltPonPortVoltageAlarmUpLimitEnable OBJECT-TYPE
              SYNTAX  INTEGER{
                              enable(1),
                              disable(2)
                             }
              ACCESS  read-write
              STATUS  mandatory
              DESCRIPTION
                      ""
              ::= { gponOltPonPortOpticalParameterAlarmEntry 14 }

          gponOltPonPortVoltageAlarmUpLimitThreshold OBJECT-TYPE
              SYNTAX  INTEGER
              ACCESS  read-write
              STATUS  mandatory
              DESCRIPTION
                      ""
              ::= { gponOltPonPortOpticalParameterAlarmEntry 15 }

          gponOltPonPortVoltageAlarmUpLimitClearThreshold OBJECT-TYPE
              SYNTAX  INTEGER
              ACCESS  read-write
              STATUS  mandatory
              DESCRIPTION
                      ""
              ::= { gponOltPonPortOpticalParameterAlarmEntry 16 }

          gponOltPonPortVoltageAlarmLowLimitEnable OBJECT-TYPE
              SYNTAX  INTEGER{
                              enable(1),
                              disable(2)
                             }
              ACCESS  read-write
              STATUS  mandatory
              DESCRIPTION
                      ""
              ::= { gponOltPonPortOpticalParameterAlarmEntry 17 }

          gponOltPonPortVoltageAlarmLowLimitThreshold OBJECT-TYPE
              SYNTAX  INTEGER
              ACCESS  read-write
              STATUS  mandatory
              DESCRIPTION
                      ""
              ::= { gponOltPonPortOpticalParameterAlarmEntry 18 }

          gponOltPonPortVoltageAlarmLowLimitClearThreshold OBJECT-TYPE
              SYNTAX  INTEGER
              ACCESS  read-write
              STATUS  mandatory
              DESCRIPTION
                      ""
              ::= { gponOltPonPortOpticalParameterAlarmEntry 19 }

          gponOltPonPortCurrentAlarmUpLimitEnable OBJECT-TYPE
              SYNTAX  INTEGER{
                              enable(1),
                              disable(2)
                             }
              ACCESS  read-write
              STATUS  mandatory
              DESCRIPTION
                      ""
              ::= { gponOltPonPortOpticalParameterAlarmEntry 20 }

          gponOltPonPortCurrentAlarmUpLimitThreshold OBJECT-TYPE
              SYNTAX  INTEGER
              ACCESS  read-write
              STATUS  mandatory
              DESCRIPTION
                      ""
              ::= { gponOltPonPortOpticalParameterAlarmEntry 21 }

          gponOltPonPortCurrentAlarmUpLimitClearThreshold OBJECT-TYPE
              SYNTAX  INTEGER
              ACCESS  read-write
              STATUS  mandatory
              DESCRIPTION
                      ""
              ::= { gponOltPonPortOpticalParameterAlarmEntry 22 }

          gponOltPonPortCurrentAlarmLowLimitEnable OBJECT-TYPE
              SYNTAX  INTEGER{
                              enable(1),
                              disable(2)
                             }
              ACCESS  read-write
              STATUS  mandatory
              DESCRIPTION
                      ""
              ::= { gponOltPonPortOpticalParameterAlarmEntry 23 }

          gponOltPonPortCurrentAlarmLowLimitThreshold OBJECT-TYPE
              SYNTAX  INTEGER
              ACCESS  read-write
              STATUS  mandatory
              DESCRIPTION
                      ""
              ::= { gponOltPonPortOpticalParameterAlarmEntry 24 }

          gponOltPonPortCurrentAlarmLowLimitClearThreshold OBJECT-TYPE
              SYNTAX  INTEGER
              ACCESS  read-write
              STATUS  mandatory
              DESCRIPTION
                      ""
              ::= { gponOltPonPortOpticalParameterAlarmEntry 25 }


--OLT PON端口光功率告警陷阱
--gponOltPonSfpParameterAlarmTrap  OID:1.3.6.1.4.1.3320.10.2.5

    gponOltPonSfpParameterAlarmTrap OBJECT IDENTIFIER
                                ::= { nmsGponOltPonPortObj 5 }

          gponOltPonSfpParameterAlarmStatus OBJECT-TYPE
              SYNTAX  INTEGER{
                              above(1),
                              below(2),
                              normal(3)
                              }
              ACCESS  read-write
              STATUS  mandatory
              DESCRIPTION
                      ""
              ::= { gponOltPonSfpParameterAlarmTrap 1 }

    gponOltPonSfpParameterAlarmNotification NOTIFICATION-TYPE
            OBJECTS {
                       ifIndex,
                       ifDescr,
                       gponOltPonSfpParameterAlarmStatus,
                       gponOltPonPortOpticalParameterTemperature,
                       gponOltPonPortOpticalParameterVoltage,
                       gponOltPonPortOpticalParameterCurrent,
                       gponOltPonPortOpticalParameterTxPower
                        }
            STATUS      current
            DESCRIPTION
            "The agent generates this notification when alarm was triggered ."
            ::= { gponOltPonSfpParameterAlarmTrap 2 }
             
--PON口与ONU绑定关系表

--gponOltONUBindTable  OID:1.3.6.1.4.1.3320.10.2.6

             gponOltONUBindTable OBJECT-TYPE
                 SYNTAX  SEQUENCE OF GponOltONUBindEntry
                 ACCESS  not-accessible
                 STATUS  mandatory
                 DESCRIPTION
                          "gpon Olt Pon Port and onu binding table."
                 ::= { nmsGponOltPonPortObj 6 }

             gponOltONUBindEntry OBJECT-TYPE
                 SYNTAX GponOltONUBindEntry
                 ACCESS  not-accessible
                 STATUS  mandatory
                 DESCRIPTION
                          "gpon Olt Pon Port and onu binding entry ."
                 INDEX { gponOltONUBindPortIndex }
             ::= { gponOltONUBindTable 1 }

             GponOltONUBindEntry ::=
                 SEQUENCE {
                     gponOltONUBindPortIndex
                         INTEGER,
                     gponOltONUBindONUId
                         INTEGER,
                     gponOltONUBindSN 
                         OCTET STRING,
                      gponOltONUBindPassword 
                         OCTET STRING,
                     gponOltONUBindRowStatus 
                         RowStatus
                      
                 }
                 
                 
          gponOltONUBindPortIndex OBJECT-TYPE
              SYNTAX  INTEGER
              ACCESS  read-only
              STATUS  mandatory

              DESCRIPTION
                      "Pon port diID."
              ::= { gponOltONUBindEntry 1 }

          gponOltONUBindONUId OBJECT-TYPE
              SYNTAX  INTEGER(1..128)
              ACCESS  read-write
              STATUS  mandatory

              DESCRIPTION
                      "ONU ID (1-128)."
              ::= { gponOltONUBindEntry 2 }

          gponOltONUBindSN OBJECT-TYPE
              SYNTAX  OCTET STRING
              ACCESS  read-write
              STATUS  mandatory

              DESCRIPTION
                      "Serial number of ONU."
              ::= { gponOltONUBindEntry 3 }

          gponOltONUBindPassword OBJECT-TYPE
              SYNTAX  OCTET STRING
              ACCESS  read-write
              STATUS  mandatory

              DESCRIPTION
                      "Password."
              ::= { gponOltONUBindEntry 4 }

          gponOltONUBindRowStatus OBJECT-TYPE
              SYNTAX  RowStatus
              ACCESS  read-create
              STATUS  mandatory

              DESCRIPTION
                      "."
              ::= { gponOltONUBindEntry 5 }
           
              
              
--PON口与ONU LOID绑定关系表

--gponOltONUBindLoidTable  OID:1.3.6.1.4.1.3320.10.2.7

             gponOltONUBindLoidTable OBJECT-TYPE
                 SYNTAX  SEQUENCE OF GponOltONUBindLoidEntry
                 ACCESS  not-accessible
                 STATUS  mandatory
                 DESCRIPTION
                          "gpon Olt Pon Port and onu LOID binding table."
                 ::= { nmsGponOltPonPortObj 7 }

             gponOltONUBindLoidEntry OBJECT-TYPE
                 SYNTAX GponOltONUBindLoidEntry
                 ACCESS  not-accessible
                 STATUS  mandatory
                 DESCRIPTION
                          "gpon Olt Pon Port and onu LOID binding entry ."
                 INDEX { gponOltONUBindPortIndex }
             ::= { gponOltONUBindLoidTable 1 }

             GponOltONUBindLoidEntry ::=
                 SEQUENCE {
                     gponOltONUBindLoidPortIndex
                         INTEGER,
                     gponOltONUBindLoidONUId
                         INTEGER,
                     gponOltONUBindLOID 
                         OCTET STRING,
                      gponOltONUBindLoidPassword 
                         OCTET STRING,
                     gponOltONUBindLoidRowStatus 
                         RowStatus
                      
                 }
                 
                 
          gponOltONUBindLoidPortIndex OBJECT-TYPE
              SYNTAX  INTEGER
              ACCESS  read-only
              STATUS  mandatory

              DESCRIPTION
                      "Pon port diID."
              ::= { gponOltONUBindLoidEntry 1 }

          gponOltONUBindLoidONUId OBJECT-TYPE
              SYNTAX  INTEGER(1..128)
              ACCESS  read-write
              STATUS  mandatory

              DESCRIPTION
                      "ONU ID (1-128)."
              ::= { gponOltONUBindLoidEntry 2 }

          gponOltONUBindLOID OBJECT-TYPE
              SYNTAX  OCTET STRING
              ACCESS  read-write
              STATUS  mandatory

              DESCRIPTION
                      "Logical ID of ONU."
              ::= { gponOltONUBindLoidEntry 3 }

          gponOltONUBindLoidPassword OBJECT-TYPE
              SYNTAX  OCTET STRING
              ACCESS  read-write
              STATUS  mandatory

              DESCRIPTION
                      "Password."
              ::= { gponOltONUBindLoidEntry 4 }

          gponOltONUBindLoidRowStatus OBJECT-TYPE
              SYNTAX  RowStatus
              ACCESS  read-create
              STATUS  mandatory

              DESCRIPTION
                      "."
              ::= { gponOltONUBindLoidEntry 5 }


-- Disable ONU list

             gponOltOnuDisableTable OBJECT-TYPE
                 SYNTAX  SEQUENCE OF GponOltOnuDisableEntry
                 ACCESS  not-accessible
                 STATUS  mandatory
                 DESCRIPTION
                          "Disable ONU table."
                 ::= { nmsGponOltPonPortObj 8 }
                
             gponOltOnuDisableEntry OBJECT-TYPE
                 SYNTAX  GponOltOnuDisableEntry
                 ACCESS  not-accessible
                 STATUS  mandatory
                 DESCRIPTION
                          "Disable ONU table entry."
                 INDEX { gponOltOnuDisablePortIndex, gponOltOnuDisableEntryIndex }
                 ::= { gponOltOnuDisableTable 1 }
                
             GponOltOnuDisableEntry ::=
                 SEQUENCE {
                     gponOltOnuDisablePortIndex
                         INTEGER,
                     gponOltOnuDisableEntryIndex
                         INTEGER,
                     gponOltOnuDisableInterface
                         OCTET STRING,
                     gponOltOnuDisableTime
                         DateAndTime,
                     gponOltOnuDisableReason
                         INTEGER,
                     gponOltOnuDisableSn
                         OCTET STRING,
                     gponOltOnuDisableSnPassword
                         OCTET STRING,
                     gponOltOnuDisableLoid
                         OCTET STRING,
                     gponOltOnuDisableLoidPassword
                         OCTET STRING
                }
                
             
             gponOltOnuDisablePortIndex OBJECT-TYPE
                 SYNTAX  INTEGER
                 ACCESS  read-only
                 STATUS  mandatory
                
                 DESCRIPTION
                         ""
                 ::= { gponOltOnuDisableEntry 1 }
                
             gponOltOnuDisableEntryIndex OBJECT-TYPE
                 SYNTAX  INTEGER
                 ACCESS  read-only
                 STATUS  mandatory
                 
                 DESCRIPTION
                          ""
                 ::= { gponOltOnuDisableEntry 2 }
            
             gponOltOnuDisableInterface OBJECT-TYPE
                 SYNTAX  OCTET STRING
                 ACCESS  read-only
                 STATUS  mandatory
                 
                 DESCRIPTION
                          "Interface of disable ONU."
                 ::= { gponOltOnuDisableEntry 3 }
                 
             gponOltOnuDisableTime OBJECT-TYPE
                 SYNTAX  DateAndTime
                 ACCESS  read-only
                 STATUS  mandatory
                 
                 DESCRIPTION
                          ""
                 ::= { gponOltOnuDisableEntry 4 }
                          
             gponOltOnuDisableReason OBJECT-TYPE
                 SYNTAX  INTEGER { 
                        sn-unknown(1),
                        password-mismatch(2),
                        anti-rogue(3),
                        ranging-failed(4),
                        loid-auth-failed(5),
                        manual(6)
                    }
                 ACCESS  read-only
                 STATUS  mandatory
                 
                 DESCRIPTION
                          ""
                 ::= { gponOltOnuDisableEntry 5 }
                 
             gponOltOnuDisableSn OBJECT-TYPE
                 SYNTAX  OCTET STRING
                 ACCESS  read-only
                 STATUS  mandatory
                 
                 DESCRIPTION
                          "Serial Number of the disabled ONU"
                 ::= { gponOltOnuDisableEntry 6 }
                 
             gponOltOnuDisableSnPassword OBJECT-TYPE
                 SYNTAX  OCTET STRING
                 ACCESS  read-only
                 STATUS  mandatory
                 
                 DESCRIPTION
                          "Password of the disabled ONU. Only valid when authentication methos is SN+Password."
                 ::= { gponOltOnuDisableEntry 7 }
                 
             gponOltOnuDisableLoid OBJECT-TYPE
                 SYNTAX  OCTET STRING
                 ACCESS  read-only
                 STATUS  mandatory
                 
                 DESCRIPTION 
                          "Logical id of the disabled ONU. Only valid when authentication methos is LOID."
                 ::= { gponOltOnuDisableEntry 8 }

             gponOltOnuDisableLoidPassword OBJECT-TYPE
                 SYNTAX  OCTET STRING
                 ACCESS  read-only
                 STATUS  mandatory
                 
                 DESCRIPTION 
                          "Password of the Logical id of the disabled ONU. Only valid when authentication methos is LOID."
                 ::= { gponOltOnuDisableEntry 9 }


--PON口与ONU绑定关系表

--gponOltONUBindPasswdOnlyTable  OID:1.3.6.1.4.1.3320.10.2.9

             gponOltONUBindPasswdOnlyTable OBJECT-TYPE
                 SYNTAX  SEQUENCE OF GponOltONUBindPasswdOnlyEntry
                 ACCESS  not-accessible
                 STATUS  mandatory
                 DESCRIPTION
                          "gpon Olt Pon Port and onu passwordonly binding table."
                 ::= { nmsGponOltPonPortObj 9 }

             gponOltONUBindPasswdOnlyEntry OBJECT-TYPE
                 SYNTAX GponOltONUBindPasswdOnlyEntry
                 ACCESS  not-accessible
                 STATUS  mandatory
                 DESCRIPTION
                          "gpon Olt Pon Port and onu passwordonly binding entry ."
                 INDEX { gponOltONUBindPasswdOnlyPortIndex }
             ::= { gponOltONUBindPasswdOnlyTable 1 }

             GponOltONUBindPasswdOnlyEntry ::=
                 SEQUENCE {
                     gponOltONUBindPasswdOnlyPortIndex
                         INTEGER,
                     gponOltONUBindPasswdOnlyONUId
                         INTEGER,
                      gponOltONUBindPasswdOnlyPassword 
                         OCTET STRING,
                     gponOltONUBindPasswdOnlyRowStatus 
                         RowStatus
                      
                 }
                 
                 
          gponOltONUBindPasswdOnlyPortIndex OBJECT-TYPE
              SYNTAX  INTEGER
              ACCESS  read-only
              STATUS  mandatory

              DESCRIPTION
                      "Pon port diID."
              ::= { gponOltONUBindPasswdOnlyEntry 1 }

          gponOltONUBindPasswdOnlyONUId OBJECT-TYPE
              SYNTAX  INTEGER(1..128)
              ACCESS  read-write
              STATUS  mandatory

              DESCRIPTION
                      "ONU ID (1-128)."
              ::= { gponOltONUBindPasswdOnlyEntry 2 }

          gponOltONUBindPasswdOnlyPassword OBJECT-TYPE
              SYNTAX  OCTET STRING
              ACCESS  read-write
              STATUS  mandatory

              DESCRIPTION
                      "Password."
              ::= { gponOltONUBindPasswdOnlyEntry 3 }

          gponOltONUBindPasswdOnlyRowStatus OBJECT-TYPE
              SYNTAX  RowStatus
              ACCESS  read-create
              STATUS  mandatory

              DESCRIPTION
                      "."
              ::= { gponOltONUBindPasswdOnlyEntry 4 }
           

--nmsGponONUObj ONU任务 OID:1.3.6.1.4.1.3320.10.3

nmsGponONUObj   OBJECT IDENTIFIER ::= { nmsGponMIB 3 }  

-- ONU基本信息表

             gponOnuInfoTable OBJECT-TYPE
                 SYNTAX  SEQUENCE OF GponOnuInfoEntry
                 ACCESS  not-accessible
                 STATUS  mandatory
                 DESCRIPTION
                          "GPON onu information table."
                 ::= { nmsGponONUObj 1 }

             gponOnuInfoEntry OBJECT-TYPE
                 SYNTAX GponOnuInfoEntry
                 ACCESS  not-accessible
                 STATUS  mandatory
                 DESCRIPTION
                          "gpon onu information table."
                 INDEX { gponONUInfoDeviceIndex }
             ::= { gponOnuInfoTable 1 }

             GponOnuInfoEntry ::=
                 SEQUENCE {
                      gponONUInfoDeviceIndex
                         INTEGER,
                      onuVendorID
                         OCTET STRING,
                      onuVersion 
                         OCTET STRING,
                      onuSerialNum 
                         OCTET STRING,
                      onuTrafficManagementOption 
                         INTEGER,
                      onuBatteryBackup 
                         INTEGER,
                      onuAdminState 
                         INTEGER,
                      onuOperationalState 
                         INTEGER,
                      onuEquipmentID 
                         OCTET STRING,
                      onuOMCCVersion 
                         INTEGER,
                      onuHardwareType 
                         INTEGER,
                      onuHardwareRevision 
                         INTEGER,
                      onuSecurityCapability 
                         INTEGER,
                      onuSecurityMode 
                         INTEGER,
                      onuTotalPriorityQueueNumber 
                         INTEGER,
                      onuTotalTrafficSchedulerNumber 
                         INTEGER,
                      onuTotalGEMPortNumber 
                         INTEGER,
                      onuTotalPOTSUNInumber 
                         INTEGER,
                      onuSysUpTime 
                         INTEGER,
                      onuImageInstance0Version 
                         OCTET STRING,
                      onuImageInstance0Valid 
                         INTEGER,
                      onuImageInstance0Activate 
                         INTEGER,
                      onuImageInstance0Commit 
                         INTEGER,
                      onuImageInstance1Version 
                         OCTET STRING,
                      onuImageInstance1Valid 
                         INTEGER,
                      onuImageInstance1Activate 
                         INTEGER,
                      onuImageInstance1Commit 
                         INTEGER,
                      onuInfoOnuMacAddress 
                         PhysAddress,
                      onuFastLeaveCapability 
                         INTEGER,
                      onuPiggybackDbaRep 
                         INTEGER,
                      onuWholeOnuDbaRep 
                         INTEGER,
                      onuProtectionMode 
                         INTEGER,
                      onuDistance 
                         INTEGER,
                      onuSwdlState 
                         INTEGER,
                     onuDeActiveReason 
                         INTEGER,
                     onuPoeSupplyVoltage
                         INTEGER,
                     onuPoeTemperLimit
                         INTEGER,    
                     onuTotalCATVUNINumber
                         INTEGER,
                     onuTotalCATVPriUNINumber
                         INTEGER, 
                     onuTotalEthernetUNInumber
                         INTEGER,    
                     onuTotalVEIPnumber
                         INTEGER,
                     onuTotalIpHostnumber
                         INTEGER,
                     onuTotalOtherUNInumber
                         INTEGER,
                     onuTotalGeneralUNInumber
                         INTEGER
                 }
                 
                 
          gponONUInfoDeviceIndex OBJECT-TYPE
              SYNTAX  INTEGER
              ACCESS  read-only
              STATUS  mandatory

              DESCRIPTION
                      "Pon port diID."
              ::= { gponOnuInfoEntry 1 }

          onuVendorID OBJECT-TYPE
              SYNTAX  OCTET STRING
              ACCESS  read-only
              STATUS  mandatory

              DESCRIPTION
                      "This attribute identifies the vendor of the ONT. It is the same as the four most significant
                       bytes of the ONT serial number (4 bytes). "
              ::= { gponOnuInfoEntry 2 }

          onuVersion OBJECT-TYPE
              SYNTAX  OCTET STRING
              ACCESS  read-only
              STATUS  mandatory

              DESCRIPTION
                      "This attribute identifies the version of the ONT as defined by the vendor. Then character
                       value“0” indicates that version information is not available or applicable.(14 bytes) "
              ::= { gponOnuInfoEntry 3 }

          onuSerialNum OBJECT-TYPE
              SYNTAX  OCTET STRING
              ACCESS  read-only
              STATUS  mandatory

              DESCRIPTION
                      "The serial number is unique for each ONT. It contains the vendor id and version number in
                       hexadecimal format. "
              ::= { gponOnuInfoEntry 4 }

          onuTrafficManagementOption OBJECT-TYPE
              SYNTAX  INTEGER{
                               priority-controlled(0),
                               rate-controlled(1),
                               priority-and-rate-controlled(2)
                              }
              
              ACCESS  read-only
              STATUS  mandatory

              DESCRIPTION
                      "This attribute identifies the upstream traffic management function implemented in the ONT. 
                      There are two options: 0 Priority controlled and flexibly scheduled upstream traffic. The 
                      traffic scheduler and priority queue mechanism are used for upstream traffic. 1 Rate controlled
                       upstream traffic. The maximum upstream traffic of each individual connection is guaranteed .2
                        Priority and rate controlled. The traffic scheduler and priority queue mechanism are used for 
                        upstream traffic. The maximum upstream traffic of each individual connection is guaranteed by 
                        shaping. "
              ::= { gponOnuInfoEntry 5 }

          onuBatteryBackup OBJECT-TYPE
              SYNTAX  INTEGER{
                               true(1),
                               false(2)
                              }
              ACCESS  read-write
              STATUS  mandatory

              DESCRIPTION
                      "his Boolean attribute specifies whether the ONT/NT supports backup battery monitoring. False
                       disables battery alarm monitoring; True enables battery alarm monitoring. (1 byte). Default 
                       value is false. "
              ::= { gponOnuInfoEntry 6 }

          onuAdminState OBJECT-TYPE
              SYNTAX  INTEGER{
                               noshutdown-unlocks(1),
                               shutdown-locks(2)
                              }
              ACCESS  read-write
              STATUS  mandatory

              DESCRIPTION
                      "1 No shutdown/unlocks, 2 Shutdown/locks. "
              ::= { gponOnuInfoEntry 7 }

          onuOperationalState OBJECT-TYPE
              SYNTAX  INTEGER{
                               enable(1),
                               disable(2)
                              }
              ACCESS  read-only
              STATUS  mandatory

              DESCRIPTION
                      "1 Enabled 2 Disable."
              ::= { gponOnuInfoEntry 8 }

          onuEquipmentID OBJECT-TYPE
              SYNTAX  OCTET STRING
              ACCESS  read-only
              STATUS  mandatory

              DESCRIPTION
                      "This attribute may be used to identify the specific type of ONT. "
              ::= { gponOnuInfoEntry 9 }

          onuOMCCVersion OBJECT-TYPE
              SYNTAX  INTEGER
              ACCESS  read-only
              STATUS  mandatory

              DESCRIPTION
                      ""
              ::= { gponOnuInfoEntry 10 }

          onuHardwareType OBJECT-TYPE
              SYNTAX  INTEGER
              ACCESS  read-only
              STATUS  mandatory

              DESCRIPTION
                      ""
              ::= { gponOnuInfoEntry 11 }

          onuHardwareRevision OBJECT-TYPE
              SYNTAX  INTEGER
              ACCESS  read-only
              STATUS  mandatory

              DESCRIPTION
                      ""
              ::= { gponOnuInfoEntry 12 }

          onuSecurityCapability OBJECT-TYPE
              SYNTAX  INTEGER
              ACCESS  read-only
              STATUS  mandatory

              DESCRIPTION
                      ""
              ::= { gponOnuInfoEntry 13 }

          onuSecurityMode OBJECT-TYPE
              SYNTAX  INTEGER(1..255)
              ACCESS  read-write
              STATUS  mandatory

              DESCRIPTION
                      "This attribute specifies the current security mode of the ONT. All secure
                       GEM ports in an ONT must use the same security mode at any given time. The
                       following codepoints are defined: 1 Reserved 2 AES algorithm 3..255 Reserved. "
              ::= { gponOnuInfoEntry 14 }

          onuTotalPriorityQueueNumber OBJECT-TYPE
              SYNTAX  INTEGER
              ACCESS  read-only
              STATUS  mandatory

              DESCRIPTION
                      ""
              ::= { gponOnuInfoEntry 15 }

          onuTotalTrafficSchedulerNumber OBJECT-TYPE
              SYNTAX  INTEGER
              ACCESS  read-only
              STATUS  mandatory

              DESCRIPTION
                      ""
              ::= { gponOnuInfoEntry 16 }

          onuTotalGEMPortNumber OBJECT-TYPE
              SYNTAX  INTEGER
              ACCESS  read-only
              STATUS  mandatory

              DESCRIPTION
                      ""
              ::= { gponOnuInfoEntry 17 }

          onuTotalPOTSUNInumber OBJECT-TYPE
              SYNTAX  INTEGER
              ACCESS  read-only
              STATUS  mandatory

              DESCRIPTION
                      ""
              ::= { gponOnuInfoEntry 18 }

          onuSysUpTime OBJECT-TYPE
              SYNTAX  INTEGER
              ACCESS  read-only
              STATUS  mandatory

              DESCRIPTION
                      ""
              ::= { gponOnuInfoEntry 19 }

          onuImageInstance0Version OBJECT-TYPE
              SYNTAX  OCTET STRING
              ACCESS  read-only
              STATUS  mandatory

              DESCRIPTION
                      ""
              ::= { gponOnuInfoEntry 20 }

          onuImageInstance0Valid OBJECT-TYPE
              SYNTAX  INTEGER{
                               true(1),
                               false(2)
                              }
              ACCESS  read-only
              STATUS  mandatory

              DESCRIPTION
                      ""
              ::= { gponOnuInfoEntry 21 }

          onuImageInstance0Activate OBJECT-TYPE
              SYNTAX  INTEGER{
                               true(1),
                               false(2)
                              }
              ACCESS  read-only
              STATUS  mandatory

              DESCRIPTION
                      ""
              ::= { gponOnuInfoEntry 22 }

          onuImageInstance0Commit OBJECT-TYPE
              SYNTAX  INTEGER{
                               true(1),
                               false(2)
                              }
              ACCESS  read-only
              STATUS  mandatory

              DESCRIPTION
                      ""
              ::= { gponOnuInfoEntry 23 }

          onuImageInstance1Version OBJECT-TYPE
              SYNTAX  OCTET STRING
              ACCESS  read-only
              STATUS  mandatory

              DESCRIPTION
                      ""
              ::= { gponOnuInfoEntry 24 }

          onuImageInstance1Valid OBJECT-TYPE
              SYNTAX  INTEGER{
                               true(1),
                               false(2)
                              }
              ACCESS  read-only
              STATUS  mandatory

              DESCRIPTION
                      ""
              ::= { gponOnuInfoEntry 25 }

          onuImageInstance1Activate OBJECT-TYPE
              SYNTAX  INTEGER{
                               true(1),
                               false(2)
                              }
              ACCESS  read-only
              STATUS  mandatory

              DESCRIPTION
                      ""
              ::= { gponOnuInfoEntry 26 }

          onuImageInstance1Commit OBJECT-TYPE
              SYNTAX  INTEGER{
                               true(1),
                               false(2)
                              }
              ACCESS  read-only
              STATUS  mandatory

              DESCRIPTION
                      ""
              ::= { gponOnuInfoEntry 27 }

          onuInfoOnuMacAddress OBJECT-TYPE
              SYNTAX  PhysAddress
              ACCESS  read-only
              STATUS  mandatory

              DESCRIPTION
                      ""
              ::= { gponOnuInfoEntry 28 }

          onuFastLeaveCapability OBJECT-TYPE
              SYNTAX  INTEGER
              ACCESS  read-only
              STATUS  mandatory

              DESCRIPTION
                      ""
              ::= { gponOnuInfoEntry 29 }

          onuPiggybackDbaRep OBJECT-TYPE
              SYNTAX  INTEGER
              ACCESS  read-only
              STATUS  mandatory

              DESCRIPTION
                      ""
              ::= { gponOnuInfoEntry 30 }

          onuWholeOnuDbaRep OBJECT-TYPE
              SYNTAX  INTEGER
              ACCESS  read-only
              STATUS  mandatory

              DESCRIPTION
                      ""
              ::= { gponOnuInfoEntry 31 }

          onuProtectionMode OBJECT-TYPE
              SYNTAX  INTEGER{
                               type-b-scheme(1),
                               type-c-scheme(2)
                              }
              ACCESS  read-write
              STATUS  mandatory

              DESCRIPTION
                      "Indicates Protection scheme, (1) for Type-B scheme and (2) for Type-C scheme. "
              ::= { gponOnuInfoEntry 32 }

          onuDistance OBJECT-TYPE
              SYNTAX  INTEGER
              ACCESS  read-only
              STATUS  mandatory

              DESCRIPTION
                      ""
              ::= { gponOnuInfoEntry 33 }

          onuSwdlState OBJECT-TYPE
              SYNTAX  INTEGER
              ACCESS  read-only
              STATUS  mandatory

              DESCRIPTION
                      ""
              ::= { gponOnuInfoEntry 34 }

          onuDeActiveReason OBJECT-TYPE
              SYNTAX  INTEGER{
                               none(0),
                               dying-gasp(1),
                               laser-always-on(2),
                               admin-control(3),
                               temp-omcc-problem(4),
                               unknown(5),
                               pon-los(6),
                               lcdg(7),
                               wire-down(8),
                               omci-mismatch(9),
                               omci-linkdown(10),
                               password-mismatch(11),
                               reboot(12),
                               ranging-failed(13),
                               disable-onu(14),
                               ack-timeout(15),
                               sfi(16),
                               tiwi(17),
                               onu-alarm(18),
                               loki(19),
                               psg-switch(20)
                             }
              ACCESS  read-only
              STATUS  mandatory

              DESCRIPTION
                      ""
              ::= { gponOnuInfoEntry 35 }
              
           onuPoeSupplyVoltage OBJECT-TYPE
              SYNTAX  INTEGER
              ACCESS  read-only
              STATUS  mandatory

              DESCRIPTION
                      ""
              ::= { gponOnuInfoEntry 36 }
              
           onuPoeTemperLimit OBJECT-TYPE
              SYNTAX  INTEGER
              ACCESS  read-only
              STATUS  mandatory

              DESCRIPTION
                      ""
              ::= { gponOnuInfoEntry 37 }     
           onuTotalCATVUNINumber OBJECT-TYPE
              SYNTAX  INTEGER
              ACCESS  read-only
              STATUS  mandatory

              DESCRIPTION
                      ""
              ::= { gponOnuInfoEntry 38 }  
           onuTotalCATVPriUNINumber OBJECT-TYPE
              SYNTAX  INTEGER
              ACCESS  read-only
              STATUS  mandatory

              DESCRIPTION
                      ""
              ::= { gponOnuInfoEntry 39 }      
           onuTotalEthernetUNInumber OBJECT-TYPE
              SYNTAX  INTEGER
              ACCESS  read-only
              STATUS  mandatory

              DESCRIPTION
                      ""
              ::= { gponOnuInfoEntry 40 } 
           onuTotalVEIPnumber OBJECT-TYPE
              SYNTAX  INTEGER
              ACCESS  read-only
              STATUS  mandatory

              DESCRIPTION
                      ""
              ::= { gponOnuInfoEntry 41 }
           onuTotalIpHostnumber OBJECT-TYPE
              SYNTAX  INTEGER
              ACCESS  read-only
              STATUS  mandatory

              DESCRIPTION
                      ""
              ::= { gponOnuInfoEntry 42 }

           onuTotalOtherUNInumber OBJECT-TYPE
              SYNTAX  INTEGER
              ACCESS  read-only
              STATUS  mandatory
              
              DESCRIPTION
                      "Other UNI port number. (NOT Ethernet/VEIP/POTS/CATV)"
              ::= { gponOnuInfoEntry 43 }

           onuTotalGeneralUNInumber OBJECT-TYPE
              SYNTAX  INTEGER
              ACCESS  read-only
              STATUS  mandatory
              
              DESCRIPTION
                      "General UNI port number. (UNI-G ME) "
              ::= { gponOnuInfoEntry 44 }



--ONU 管理表

--gponOnuConfigTable  OID:1.3.6.1.4.1.3320.10.3.2

             gponOnuConfigTable OBJECT-TYPE
                 SYNTAX  SEQUENCE OF GponOnuConfigEntry
                 ACCESS  not-accessible
                 STATUS  mandatory
                 DESCRIPTION
                          "gpon  onu configuration table."
                 ::= { nmsGponONUObj 2 }

             gponOnuConfigEntry OBJECT-TYPE
                 SYNTAX GponOnuConfigEntry
                 ACCESS  not-accessible
                 STATUS  mandatory
                 DESCRIPTION
                          "gpon onu configuration entry ."
                 INDEX { gponOnuConfigDeviceIndex }
             ::= { gponOnuConfigTable 1 }

             GponOnuConfigEntry ::=
                 SEQUENCE {
                     gponOnuConfigDeviceIndex
                         INTEGER,
                     gponOnuConfigActicate
                         INTEGER,
                     gponOnuConfigEnable 
                         INTEGER,
                      gponOnuConfigReboot 
                         INTEGER,
                      gponOnuConfigEnablePM 
                         INTEGER,
                      gponOnuConfigFlowProfileID 
                         INTEGER,
                      gponOnuConfigTcontVirPortBindingProfileID 
                         INTEGER,
                      gponOnuConfigOnuProfileID 
                         INTEGER,
                     gponOnuConfigUsMapProfileID 
                         INTEGER,
                     gponOnuConfigOpticalAlarmEnable 
                         INTEGER,
                     gponOnuConfigOpticalAlarmRxLow 
                         INTEGER,
                     gponOnuConfigOpticalAlarmRxHigh 
                         INTEGER,
                     gponOnuConfigOpticalAlarmTxLow 
                         INTEGER,
                     gponOnuConfigOpticalAlarmTxHigh 
                         INTEGER,
                     gponOnuConfigFEC 
                         INTEGER, 
                     gponOnuConfigLoopbackDetectProtocol 
                         INTEGER,
                     gponOnuConfigLoopbackDetectAdminState 
                         INTEGER,
                     gponOnuConfigLoopbackDetectAutoShutoff 
                         INTEGER, 
                     gponOnuConfigCatvProtocol 
                         INTEGER,
                     gponOnuPoePowerLimit
                         INTEGER, 
                     gponOnuConfigDescription
                         OCTET STRING,
                     gponOnuConfigAlwaysChkOnutypeTemp
                         INTEGER,
                     gponOnuConfigUpstreamMacSecurity 
                         INTEGER,
                     gponOnuConfigRemoteAccessTelnet
                         INTEGER, 
                     gponOnuConfigRemoteAccessPing
                         INTEGER, 
                     gponOnuConfigRemoteAccessWebui
                         INTEGER,
                     gponOnuConfigClearLocalConfigure
                         INTEGER,
                     gponOnuConfigLoopbackDetectProfileID
                         INTEGER,
                     gponOnuConfigPoeProtocol
                         INTEGER,
                     gponOnuConfigSnmpProfileID
                         INTEGER,
                     gponOnuConfigVoiceVlanProfileID
                         INTEGER,
                     gponOnuConfigDot1xProfileID
                         INTEGER
                 }
                 
          gponOnuConfigDeviceIndex OBJECT-TYPE
              SYNTAX  INTEGER
              ACCESS  read-only
              STATUS  mandatory

              DESCRIPTION
                      "GPON ONU device configuration index."
              ::= { gponOnuConfigEntry 1 }

          gponOnuConfigActicate OBJECT-TYPE
              SYNTAX  INTEGER{
                               acticate(1),
                               deacticate(2)
                              }
              ACCESS  read-write
              STATUS  mandatory

              DESCRIPTION
                      "1-Acticate；2-Deacticate"
              ::= { gponOnuConfigEntry 2 }

          gponOnuConfigEnable OBJECT-TYPE
              SYNTAX  INTEGER{
                               enable(1),
                               disable(2)
                              }
              ACCESS  read-write
              STATUS  mandatory

              DESCRIPTION
                      "1-Enable；2-Disable."
              ::= { gponOnuConfigEntry 3 }

          gponOnuConfigReboot OBJECT-TYPE
              SYNTAX  INTEGER{
                               reboot(1)
                              }
              ACCESS  read-write
              STATUS  mandatory

              DESCRIPTION
                      "reboot(1)."
              ::= { gponOnuConfigEntry 4 }

          gponOnuConfigEnablePM OBJECT-TYPE
              SYNTAX  INTEGER{
                               enable(1),
                               disable(2)
                              }
              ACCESS  read-write
              STATUS  mandatory

              DESCRIPTION
                      ""
              ::= { gponOnuConfigEntry 5 }

          gponOnuConfigFlowProfileID OBJECT-TYPE
              SYNTAX  INTEGER
              ACCESS  read-write
              STATUS  mandatory

              DESCRIPTION
                      "The profileIndex corresponding to ONU Flow Profile Table. 0 means invalid. Default value is 1."
              ::= { gponOnuConfigEntry 6 }

          gponOnuConfigTcontVirPortBindingProfileID OBJECT-TYPE
              SYNTAX  INTEGER
              ACCESS  read-write
              STATUS  mandatory

              DESCRIPTION
                      "It points to the associated T-CONT and virtual port binding profile index. 0 means invalid."
              ::= { gponOnuConfigEntry 7 }

          gponOnuConfigOnuProfileID OBJECT-TYPE
              SYNTAX  INTEGER
              ACCESS  read-write
              STATUS  mandatory

              DESCRIPTION
                      ""
              ::= { gponOnuConfigEntry 8 }

          gponOnuConfigUsMapProfileID OBJECT-TYPE
              SYNTAX  INTEGER
              ACCESS  read-write
              STATUS  mandatory

              DESCRIPTION
                      ""
              ::= { gponOnuConfigEntry 9 }

          gponOnuConfigOpticalAlarmEnable OBJECT-TYPE
              SYNTAX  INTEGER
              ACCESS  read-write
              STATUS  mandatory

              DESCRIPTION
                      ""
              ::= { gponOnuConfigEntry 10 }

          gponOnuConfigOpticalAlarmRxLow OBJECT-TYPE
              SYNTAX  INTEGER
              ACCESS  read-write
              STATUS  mandatory

              DESCRIPTION
                      ""
              ::= { gponOnuConfigEntry 11 }

          gponOnuConfigOpticalAlarmRxHigh OBJECT-TYPE
              SYNTAX  INTEGER
              ACCESS  read-write
              STATUS  mandatory

              DESCRIPTION
                      ""
              ::= { gponOnuConfigEntry 12 }

          gponOnuConfigOpticalAlarmTxLow OBJECT-TYPE
              SYNTAX  INTEGER
              ACCESS  read-write
              STATUS  mandatory

              DESCRIPTION
                      ""
              ::= { gponOnuConfigEntry 13 }

          gponOnuConfigOpticalAlarmTxHigh OBJECT-TYPE
              SYNTAX  INTEGER
              ACCESS  read-write
              STATUS  mandatory

              DESCRIPTION
                      ""
              ::= { gponOnuConfigEntry 14 }
          
          gponOnuConfigFEC OBJECT-TYPE
              SYNTAX  INTEGER{
                               enable(1),
                               disable(2)
                              }
              ACCESS  read-write
              STATUS  mandatory

              DESCRIPTION
                      "For ONU FEC config"
              ::= { gponOnuConfigEntry 15 }
          gponOnuConfigLoopbackDetectProtocol OBJECT-TYPE
              SYNTAX  INTEGER{
                               ctc(0),
                               private(1)
                              }
              ACCESS  read-write
              STATUS  mandatory

              DESCRIPTION
                      "0-CTC；1-Private"
              ::= { gponOnuConfigEntry 16 }
          gponOnuConfigLoopbackDetectAdminState OBJECT-TYPE
              SYNTAX  INTEGER{
                               enable(0),
                               disable(1)
                              }
              ACCESS  read-write
              STATUS  mandatory

              DESCRIPTION
                      "0-Enable；1-Disable"
              ::= { gponOnuConfigEntry 17 }
          gponOnuConfigLoopbackDetectAutoShutoff OBJECT-TYPE
              SYNTAX  INTEGER{
                               enable(0),
                               disable(1)
                              }
              ACCESS  read-write
              STATUS  mandatory

              DESCRIPTION
                      "0-Enable；1-Disable"
              ::= { gponOnuConfigEntry 18 }
          gponOnuConfigCatvProtocol OBJECT-TYPE
              SYNTAX  INTEGER{
                               itu(0),
                               private(1)
                              }
              ACCESS  read-write
              STATUS  mandatory

              DESCRIPTION
                      "0-ITU；1-Private"
              ::= { gponOnuConfigEntry 19 }
          gponOnuPoePowerLimit OBJECT-TYPE
              SYNTAX  INTEGER
              ACCESS  read-write
              STATUS  mandatory

              DESCRIPTION
                      ""
              ::= { gponOnuConfigEntry 20 }  
          gponOnuConfigDescription OBJECT-TYPE
              SYNTAX  OCTET STRING
              ACCESS  read-write
              STATUS  mandatory

              DESCRIPTION
                      "The ONU description information"
              ::= { gponOnuConfigEntry 21 }
          gponOnuConfigAlwaysChkOnutypeTemp OBJECT-TYPE
              SYNTAX  INTEGER{
                               enable(1),
                               disable(2)
                              }
              ACCESS  read-write
              STATUS  mandatory

              DESCRIPTION
                      "Always check onutype template config"
              ::= { gponOnuConfigEntry 22 }
          gponOnuConfigUpstreamMacSecurity OBJECT-TYPE
              SYNTAX  INTEGER{
                               noconfig(0),
                               enable(1),
                               disable(2)
                              }
              ACCESS  read-write
              STATUS  mandatory

              DESCRIPTION
                      "Forbid onu uni-side learned mac move to pon-side"
              ::= { gponOnuConfigEntry 23 }
          gponOnuConfigRemoteAccessTelnet OBJECT-TYPE
              SYNTAX  INTEGER{
                               noconfig(0),
                               enable(1),
                               disable(2)
                              }
              ACCESS  read-write
              STATUS  mandatory

              DESCRIPTION
                      "Permit telnet onu from pon-side"
              ::= { gponOnuConfigEntry 24 }
          gponOnuConfigRemoteAccessPing OBJECT-TYPE
              SYNTAX  INTEGER{
                               noconfig(0),
                               enable(1),
                               disable(2)
                              }
              ACCESS  read-write
              STATUS  mandatory

              DESCRIPTION
                      "Permit ping onu from pon-side"
              ::= { gponOnuConfigEntry 25 }
          gponOnuConfigRemoteAccessWebui OBJECT-TYPE
              SYNTAX  INTEGER{
                               noconfig(0),
                               enable(1),
                               disable(2)
                              }
              ACCESS  read-write
              STATUS  mandatory

              DESCRIPTION
                      "Permit access onu webUI from pon-side"
              ::= { gponOnuConfigEntry 26 }
          gponOnuConfigClearLocalConfigure OBJECT-TYPE
              SYNTAX  INTEGER{
                               noconfig(0),
                               clear(1)
                              }
              ACCESS  read-write
              STATUS  mandatory

              DESCRIPTION
                      "Clear onu local configure"
              ::= { gponOnuConfigEntry 27 }
          gponOnuConfigLoopbackDetectProfileID OBJECT-TYPE
              SYNTAX  INTEGER
              ACCESS  read-write
              STATUS  mandatory

              DESCRIPTION
                      "The profile index of onuLoopbackDetection. 0 means invalid." 
              ::= { gponOnuConfigEntry 28 }
          
          gponOnuConfigPoeProtocol OBJECT-TYPE
              SYNTAX  INTEGER{
                                private(0),
                                itu(1)
                             }
              ACCESS  read-write
              STATUS  mandatory

              DESCRIPTION
                      "Poe Protocol." 
              ::= { gponOnuConfigEntry 29 }
              
          gponOnuConfigSnmpProfileID OBJECT-TYPE
              SYNTAX  INTEGER
              ACCESS  read-write
              STATUS  mandatory
              
              DESCRIPTION
                      "The profile index of onuSnmp. 0 means invalid." 
              ::= { gponOnuConfigEntry 30 }
              
          gponOnuConfigVoiceVlanProfileID OBJECT-TYPE
              SYNTAX  INTEGER
              ACCESS  read-write
              STATUS  mandatory
              
              DESCRIPTION
                      "The profile index of onu voice vlan. 0 means invalid." 
              ::= { gponOnuConfigEntry 31 }
              
          gponOnuConfigDot1xProfileID OBJECT-TYPE
              SYNTAX  INTEGER
              ACCESS  read-write
              STATUS  mandatory
              
              DESCRIPTION
                      "The profile index of onu dot1x. 0 means invalid." 
              ::= { gponOnuConfigEntry 32 }
          
--ONU 状态表        
--gponOnuStatusTable  OID:1.3.6.1.4.1.3320.10.3.3

             gponOnuStatusTable OBJECT-TYPE
                 SYNTAX  SEQUENCE OF GponOnuStatusEntry
                 ACCESS  not-accessible
                 STATUS  mandatory
                 DESCRIPTION
                          "gpon  onu status table."
                 ::= { nmsGponONUObj 3 }

             gponOnuStatusEntry OBJECT-TYPE
                 SYNTAX GponOnuStatusEntry
                 ACCESS  not-accessible
                 STATUS  mandatory
                 DESCRIPTION
                          "gpon onu status entry ."
                 INDEX { gponOnuStatusDeviceIndex }
             ::= { gponOnuStatusTable 1 }

             GponOnuStatusEntry ::=
                 SEQUENCE {
                     gponOnuStatusDeviceIndex
                         INTEGER,
                     gponOnuStatusOnuSn 
                         OCTET STRING,
                     gponOnuStatusPonPortID 
                         INTEGER,
                     gponOnuStatusOnuStatus 
                         INTEGER
                 }
                 
          gponOnuStatusDeviceIndex OBJECT-TYPE
              SYNTAX  INTEGER
              ACCESS  read-only
              STATUS  mandatory

              DESCRIPTION
                      ""
              ::= { gponOnuStatusEntry 1 }

          gponOnuStatusOnuSn OBJECT-TYPE
              SYNTAX  OCTET STRING
              ACCESS  read-only
              STATUS  mandatory

              DESCRIPTION
                      ""
              ::= { gponOnuStatusEntry 2 }

          gponOnuStatusPonPortID OBJECT-TYPE
              SYNTAX  INTEGER
              ACCESS  read-only
              STATUS  mandatory

              DESCRIPTION
                      ""
              ::= { gponOnuStatusEntry 3 }

          gponOnuStatusOnuStatus OBJECT-TYPE
              SYNTAX  INTEGER{
                              off-line(0),
                              inactive(1),
                              disable(2),
                              active(3)
                              }
              ACCESS  read-only
              STATUS  mandatory

              DESCRIPTION
                      "ONU Status. 0 off-line, 1 inactive,  2 disable, 3 active. "
              ::= { gponOnuStatusEntry 4 }

--ONU PON口光功率

--gponOnuOpticalPowerTable  OID:1.3.6.1.4.1.3320.10.3.4

             gponOnuOpticalPowerTable OBJECT-TYPE
                 SYNTAX  SEQUENCE OF GponOnuOpticalPowerEntry
                 ACCESS  not-accessible
                 STATUS  mandatory
                 DESCRIPTION
                          "gpon  onu pon port power table."
                 ::= { nmsGponONUObj 4 }

             gponOnuOpticalPowerEntry OBJECT-TYPE
                 SYNTAX GponOnuOpticalPowerEntry
                 ACCESS  not-accessible
                 STATUS  mandatory
                 DESCRIPTION
                          "gpon onu pon port power entry ."
                 INDEX { gponOnuOpticalPowerDeviceIndex }
             ::= { gponOnuOpticalPowerTable 1 }

             GponOnuOpticalPowerEntry ::=
                 SEQUENCE {
                     gponOnuOpticalPowerDeviceIndex
                         INTEGER,
                     gponOnuOpticalPowerRxPower 
                         INTEGER,
                     gponOnuOpticalPowerTxPower 
                         INTEGER,
                     gponOnuOpticalPowerVoltage 
                         INTEGER,
                     gponOnuOpticalPowerBiasCurrent 
                         INTEGER,
                     gponOnuOpticalPowerTemper 
                         INTEGER
                 }
                 
          gponOnuOpticalPowerDeviceIndex OBJECT-TYPE
              SYNTAX  INTEGER
              ACCESS  read-only
              STATUS  mandatory

              DESCRIPTION
                      ""
              ::= { gponOnuOpticalPowerEntry 1 }

          gponOnuOpticalPowerRxPower OBJECT-TYPE
              SYNTAX  INTEGER
              ACCESS  read-only
              STATUS  mandatory

              DESCRIPTION
                      "unit:0.1dBm."
              ::= { gponOnuOpticalPowerEntry 2 }

          gponOnuOpticalPowerTxPower OBJECT-TYPE
              SYNTAX  INTEGER
              ACCESS  read-only
              STATUS  mandatory

              DESCRIPTION
                      "unit:0.1dBm."
              ::= { gponOnuOpticalPowerEntry 3 }

          gponOnuOpticalPowerVoltage OBJECT-TYPE
              SYNTAX  INTEGER
              ACCESS  read-only
              STATUS  mandatory

              DESCRIPTION
                      "unit:0.1V."
              ::= { gponOnuOpticalPowerEntry 4 }

          gponOnuOpticalPowerBiasCurrent OBJECT-TYPE
              SYNTAX  INTEGER
              ACCESS  read-only
              STATUS  mandatory

              DESCRIPTION
                      "unit:0.1mA."
              ::= { gponOnuOpticalPowerEntry 5 }

          gponOnuOpticalPowerTemper OBJECT-TYPE
              SYNTAX  INTEGER
              ACCESS  read-only
              STATUS  mandatory

              DESCRIPTION
                      "unit:0.1degree."
              ::= { gponOnuOpticalPowerEntry 6 }


--ONU PON口光功率告警
--gponOnuOpticalParameterAlarmTable  OID:1.3.6.1.4.1.3320.10.3.5

             gponOnuOpticalParameterAlarmTable OBJECT-TYPE
                 SYNTAX  SEQUENCE OF GponOnuOpticalParameterAlarmEntry
                 ACCESS  not-accessible
                 STATUS  mandatory
                 DESCRIPTION
                          "gpon  onu status table."
                 ::= { nmsGponONUObj 5 }

             gponOnuOpticalParameterAlarmEntry OBJECT-TYPE
                 SYNTAX GponOnuOpticalParameterAlarmEntry
                 ACCESS  not-accessible
                 STATUS  mandatory
                 DESCRIPTION
                          "gpon onu status entry ."
                 INDEX { gponOnuOpticalParameterAlarmDeviceIndex }
             ::= { gponOnuOpticalParameterAlarmTable 1 }

             GponOnuOpticalParameterAlarmEntry ::=
                 SEQUENCE {
                     gponOnuOpticalParameterAlarmDeviceIndex
                         INTEGER,
                     gponOnuOpticalTxPowerAlarmUpLimitEnable 
                         INTEGER,
                     gponOnuOpticalTxPowerAlarmUpLimitThreshold 
                         INTEGER,
                      gponOnuOpticalTxPowerAlarmUpLimitClearThreshold 
                         INTEGER,
                     gponOnuOpticalTxPowerAlarmUpLimitRowStatus 
                         RowStatus,
                     gponOnuOpticalTxPowerAlarmLowLimitEnable 
                         INTEGER,
                     gponOnuOpticalTxPowerAlarmLowLimitThreshold 
                         INTEGER,
                     gponOnuOpticalTxPowerAlarmLowLimitClearThreshold 
                         INTEGER,
                     gponOnuOpticalTxPowerAlarmLowLimitRowStatus 
                         RowStatus,
                     gponOnuOpticalRxPowerAlarmUpLimitEnable 
                         INTEGER,
                     gponOnuOpticalRxPowerAlarmUpLimitThreshold 
                         INTEGER,
                     gponOnuOpticalRxPowerAlarmUpLimitClearThreshold 
                         INTEGER,
                     gponOnuOpticalRxPowerAlarmUpLimitRowStatus 
                         RowStatus,
                     gponOnuOpticalRxPowerAlarmLowLimitEnable 
                         INTEGER,
                     gponOnuOpticalRxPowerAlarmLowLimitThreshold 
                         INTEGER,
                     gponOnuOpticalRxPowerAlarmLowLimitClearThreshold 
                         INTEGER,
                    gponOnuOpticalRxPowerAlarmLowLimitRowStatus 
                         RowStatus
                 }
                 
          gponOnuOpticalParameterAlarmDeviceIndex OBJECT-TYPE
              SYNTAX  INTEGER
              ACCESS  read-only
              STATUS  mandatory

              DESCRIPTION
                      ""
              ::= { gponOnuOpticalParameterAlarmEntry 1 }

          gponOnuOpticalTxPowerAlarmUpLimitEnable OBJECT-TYPE
              SYNTAX  INTEGER{
                              enable(1),
                              disable(2)
                              }
              ACCESS  read-write
              STATUS  mandatory

              DESCRIPTION
                      ""
              ::= { gponOnuOpticalParameterAlarmEntry 2 }

          gponOnuOpticalTxPowerAlarmUpLimitThreshold OBJECT-TYPE
              SYNTAX  INTEGER
              ACCESS  read-write
              STATUS  mandatory

              DESCRIPTION
                      ""
              ::= { gponOnuOpticalParameterAlarmEntry 3 }

          gponOnuOpticalTxPowerAlarmUpLimitClearThreshold OBJECT-TYPE
              SYNTAX  INTEGER
              ACCESS  read-write
              STATUS  mandatory

              DESCRIPTION
                      ""
              ::= { gponOnuOpticalParameterAlarmEntry 4 }

          gponOnuOpticalTxPowerAlarmUpLimitRowStatus OBJECT-TYPE
              SYNTAX  RowStatus
              ACCESS  read-write
              STATUS  mandatory

              DESCRIPTION
                      ""
              ::= { gponOnuOpticalParameterAlarmEntry 5 }

          gponOnuOpticalTxPowerAlarmLowLimitEnable OBJECT-TYPE
              SYNTAX  INTEGER{
                              enable(1),
                              disable(2)
                              }
              ACCESS  read-write
              STATUS  mandatory

              DESCRIPTION
                      ""
              ::= { gponOnuOpticalParameterAlarmEntry 6 }

          gponOnuOpticalTxPowerAlarmLowLimitThreshold OBJECT-TYPE
              SYNTAX  INTEGER
              ACCESS  read-write
              STATUS  mandatory

              DESCRIPTION
                      ""
              ::= { gponOnuOpticalParameterAlarmEntry 7 }

          gponOnuOpticalTxPowerAlarmLowLimitClearThreshold OBJECT-TYPE
              SYNTAX  INTEGER
              ACCESS  read-write
              STATUS  mandatory

              DESCRIPTION
                      ""
              ::= { gponOnuOpticalParameterAlarmEntry 8 }

          gponOnuOpticalTxPowerAlarmLowLimitRowStatus OBJECT-TYPE
              SYNTAX  RowStatus
              ACCESS  read-write
              STATUS  mandatory

              DESCRIPTION
                      ""
              ::= { gponOnuOpticalParameterAlarmEntry 9 }

          gponOnuOpticalRxPowerAlarmUpLimitEnable OBJECT-TYPE
              SYNTAX  INTEGER{
                              enable(1),
                              disable(2)
                              }
              ACCESS  read-write
              STATUS  mandatory

              DESCRIPTION
                      ""
              ::= { gponOnuOpticalParameterAlarmEntry 10 }

          gponOnuOpticalRxPowerAlarmUpLimitThreshold OBJECT-TYPE
              SYNTAX  INTEGER
              ACCESS  read-write
              STATUS  mandatory

              DESCRIPTION
                      ""
              ::= { gponOnuOpticalParameterAlarmEntry 11 }

          gponOnuOpticalRxPowerAlarmUpLimitClearThreshold OBJECT-TYPE
              SYNTAX  INTEGER
              ACCESS  read-write
              STATUS  mandatory

              DESCRIPTION
                      ""
              ::= { gponOnuOpticalParameterAlarmEntry 12 }

          gponOnuOpticalRxPowerAlarmUpLimitRowStatus OBJECT-TYPE
              SYNTAX  RowStatus
              ACCESS  read-write
              STATUS  mandatory

              DESCRIPTION
                      ""
              ::= { gponOnuOpticalParameterAlarmEntry 13 }

          gponOnuOpticalRxPowerAlarmLowLimitEnable OBJECT-TYPE
              SYNTAX  INTEGER{
                              enable(1),
                              disable(2)
                              }
              ACCESS  read-write
              STATUS  mandatory

              DESCRIPTION
                      ""
              ::= { gponOnuOpticalParameterAlarmEntry 14 }

          gponOnuOpticalRxPowerAlarmLowLimitThreshold OBJECT-TYPE
              SYNTAX  INTEGER
              ACCESS  read-write
              STATUS  mandatory

              DESCRIPTION
                      ""
              ::= { gponOnuOpticalParameterAlarmEntry 15 }

          gponOnuOpticalRxPowerAlarmLowLimitClearThreshold OBJECT-TYPE
              SYNTAX  INTEGER
              ACCESS  read-write
              STATUS  mandatory

              DESCRIPTION
                      ""
              ::= { gponOnuOpticalParameterAlarmEntry 16 }

          gponOnuOpticalRxPowerAlarmLowLimitRowStatus OBJECT-TYPE
              SYNTAX  RowStatus
              ACCESS  read-write
              STATUS  mandatory

              DESCRIPTION
                      ""
              ::= { gponOnuOpticalParameterAlarmEntry 17 }

--ONU PON口光功率告警陷阱

    gponOnuSfpParameterAlarmTrap OBJECT IDENTIFIER
                                ::= { nmsGponONUObj 6 }
                                
                                
          gponOnuSfpParameterAlarmStatus OBJECT-TYPE
              SYNTAX  INTEGER{
                               above(1),
                               below(2),
                               normal(3)
                              }
              ACCESS  read-only
              STATUS  mandatory

              DESCRIPTION
                      ""
              ::= { gponOnuSfpParameterAlarmTrap 1 }


          gponOnuSfpParameterAlarmThreshold OBJECT-TYPE
              SYNTAX  INTEGER
              ACCESS  read-only
              STATUS  mandatory

              DESCRIPTION
                      ""
              ::= { gponOnuSfpParameterAlarmTrap 2 }


                                


    gponOnuSfpParameterAlarmNotification NOTIFICATION-TYPE
            OBJECTS {
                       ifIndex,
                       ifDescr,
                       onuSerialNum,
                       gponOnuSfpParameterAlarmStatus,
                       gponOnuOpticalPowerRxPower,
                       gponOnuOpticalPowerTxPower
            }
            STATUS      current
            DESCRIPTION
            "The agent generates this notification when ONU SFP parameter alarms ."
            ::= { gponOnuSfpParameterAlarmTrap 3 }


-- ONU 状态变化陷阱 
 
    gponOnuStatusAlarmTrap OBJECT IDENTIFIER
                                ::= { nmsGponONUObj 7 }
                                
                                
          gponOnuStatusChange OBJECT-TYPE
              SYNTAX  INTEGER{
                              discovered(1),
                              activated(2),
                              deactivated(3),
                              disable-complete(4),
                              enable-complete(5),
                              mib-reset(6),
                              mib-ready(7),
                              mib-not-ready(8),
                              onu-los(9), 
                              removed(11),
                              rejected(12)
                              }
              ACCESS  read-only
              STATUS  mandatory

              DESCRIPTION
                      ""
              ::= { gponOnuStatusAlarmTrap 1 }

                                


    gponOnuStatusChangeNotification NOTIFICATION-TYPE
            OBJECTS {
                       ifIndex,
                       ifDescr,
                       onuSerialNum,
                       onuVendorID,
                       onuEquipmentID,
                       gponOnuStatusChange,
                       onuDeActiveReason
            }
            STATUS      current
            DESCRIPTION
            "The agent generates this notification when ONU status change alarms ."
            ::= { gponOnuStatusAlarmTrap 2 }
 
-- ONU Dying Gasp陷阱

    gponOnuDyingGaspAlarmTrap OBJECT IDENTIFIER
                                ::= { nmsGponONUObj 8 }
                                
                                
          gponOnuDyingGaspStatus OBJECT-TYPE
              SYNTAX  INTEGER{
                              true(1),
                              false(2)
            }
              ACCESS  read-only
              STATUS  mandatory

              DESCRIPTION
                      ""
              ::= { gponOnuDyingGaspAlarmTrap 1 }

                                


    gponOnuDyingGaspNotification NOTIFICATION-TYPE
            OBJECTS {
                       ifIndex,
                       ifDescr,
                       onuSerialNum,
                       gponOnuDyingGaspStatus 
            }
            STATUS      current
            DESCRIPTION
            "The agent generates this notification when ONU status change alarms ."
            ::= { gponOnuDyingGaspAlarmTrap 2 }

-- ONU批量升级

             gponOnuBatchUpdateTable OBJECT-TYPE
                 SYNTAX  SEQUENCE OF GponOnuBatchUpdateEntry
                 ACCESS  not-accessible
                 STATUS  mandatory
                 DESCRIPTION
                          "Onu batch update table."
                 ::= { nmsGponONUObj 9 }

             gponOnuBatchUpdateEntry OBJECT-TYPE
                 SYNTAX GponOnuBatchUpdateEntry
                 ACCESS  not-accessible
                 STATUS  mandatory
                 DESCRIPTION
                          "Onu batch update table entry."
                 INDEX { gponOnuBatchUpdateLLIDs }
             ::= { gponOnuBatchUpdateTable 1 }

             GponOnuBatchUpdateEntry ::=
                 SEQUENCE {
                     gponOnuBatchUpdateLLIDs
                         OCTET STRING,
                     gponOnuBatchUpdateFileName
                         OCTET STRING,
                     gponOnuBatchUpdateAction
                         INTEGER,
                     gponOnuBatchUpdateResult
                         OCTET STRING
            }
                 
                 
          gponOnuBatchUpdateLLIDs OBJECT-TYPE
              SYNTAX  OCTET STRING
              ACCESS  write-only
              STATUS  mandatory

              DESCRIPTION
                      "ONU LLID list, which defines the ONU to be updated. such as (1,3,5,7) Or (1,3-5,7) Or (1-7)"
              ::= { gponOnuBatchUpdateEntry 1 }

                 
          gponOnuBatchUpdateFileName OBJECT-TYPE
              SYNTAX  OCTET STRING
              ACCESS  write-only
              STATUS  mandatory

              DESCRIPTION
                      "The file name in OLT flash, which is ONU bin file and must be existed."
              ::= { gponOnuBatchUpdateEntry 2 }

                 
          gponOnuBatchUpdateAction OBJECT-TYPE
              SYNTAX  INTEGER{
                               no-action(0),
                               action(1),
                               action-for-actvie(2)
                               
                             }
              ACCESS  write-only
              STATUS  mandatory

              DESCRIPTION
                      "The update operation indication. 0-no action for update 1-action for update. 2-action for activate.
                      3-action for commit."
              ::= { gponOnuBatchUpdateEntry 3 }

                 
          gponOnuBatchUpdateResult OBJECT-TYPE
              SYNTAX  OCTET STRING
              ACCESS  read-only
              STATUS  mandatory

              DESCRIPTION
                      "The result for update. String format: diID=resultCode,diID2=resultCode...
                      Result Code:
                       0 success
                       1 start downloading
                       2 start download failed
                       3 download finished
                       4 download failed
                       5 startup with new image failed or commit new image failed."
              ::= { gponOnuBatchUpdateEntry 4 }
 
-- Onu Optical Alarm陷阱

    gponOnuOpticalAlarmTrap OBJECT IDENTIFIER
                                ::= { nmsGponONUObj 10 }


        gponOnuOpRxLowStatus OBJECT-TYPE
              SYNTAX  INTEGER{
                              alarm(1),
                              clear(2)
            }
              ACCESS  read-only
              STATUS  mandatory

              DESCRIPTION
                      ""
              ::= { gponOnuOpticalAlarmTrap 1 }


        gponOnuOpRxLowNotification NOTIFICATION-TYPE
            OBJECTS {
                       ifIndex,
                       ifDescr,
                       onuSerialNum,
                       gponOnuOpRxLowStatus,
                       rxPower,
                       lowThreshold 
            }
            STATUS      current
            DESCRIPTION
            "The agent generates this notification when ONU status change alarms ."
            ::= { gponOnuOpticalAlarmTrap 2 }


        gponOnuOpRxHighStatus OBJECT-TYPE
              SYNTAX  INTEGER{
                              alarm(1),
                              clear(2)
            }
              ACCESS  read-only
              STATUS  mandatory

              DESCRIPTION
                      ""
              ::= { gponOnuOpticalAlarmTrap 3 }


        gponOnuOpRxHighNotification NOTIFICATION-TYPE
            OBJECTS {
                       ifIndex,
                       ifDescr,
                       onuSerialNum,
                       gponOnuOpRxHighStatus,
                       rxPower,
                       upThreshold 
            }
            STATUS      current
            DESCRIPTION
            "The agent generates this notification when ONU status change alarms ."
            ::= { gponOnuOpticalAlarmTrap 4 }


        gponOnuOpTxLowStatus OBJECT-TYPE
              SYNTAX  INTEGER{
                              alarm(1),
                              clear(2)
            }
              ACCESS  read-only
              STATUS  mandatory

              DESCRIPTION
                      ""
              ::= { gponOnuOpticalAlarmTrap 5 }


        gponOnuOpTxLowNotification NOTIFICATION-TYPE
            OBJECTS {
                       ifIndex,
                       ifDescr,
                       onuSerialNum,
                       gponOnuOpTxLowStatus,
                       txPower,
                       lowThreshold 
            }
            STATUS      current
            DESCRIPTION
            "The agent generates this notification when ONU status change alarms ."
            ::= { gponOnuOpticalAlarmTrap 6 }


        gponOnuOpTxHighStatus OBJECT-TYPE
              SYNTAX  INTEGER{
                              alarm(1),
                              clear(2)
            }
              ACCESS  read-only
              STATUS  mandatory

              DESCRIPTION
                      ""
              ::= { gponOnuOpticalAlarmTrap 7 }


        gponOnuOpTxHighNotification NOTIFICATION-TYPE
            OBJECTS {
                       ifIndex,
                       ifDescr,
                       onuSerialNum,
                       gponOnuOpTxHighStatus,
                       txPower,
                       upThreshold 
            }
            STATUS      current
            DESCRIPTION
            "The agent generates this notification when ONU status change alarms ."
            ::= { gponOnuOpticalAlarmTrap 8 }
 
 -- ONU IP 配置

             gponOnuIPParamConfigTable OBJECT-TYPE
                 SYNTAX  SEQUENCE OF GponOnuIPParamConfigEntry
                 ACCESS  not-accessible
                 STATUS  mandatory
                 DESCRIPTION
                          "Onu IP config table."
                 ::= { nmsGponONUObj 11 }

             gponOnuIPParamConfigEntry OBJECT-TYPE
                 SYNTAX GponOnuIPParamConfigEntry
                 ACCESS  not-accessible
                 STATUS  mandatory
                 DESCRIPTION
                          "Onu IP config table entry."
                 INDEX { gponOnuIPParamConfigIfIndex }
             ::= { gponOnuIPParamConfigTable 1 }

             GponOnuIPParamConfigEntry ::=
                 SEQUENCE {
                     gponOnuIPParamConfigIfIndex
                         INTEGER,
                     gponOnuIPParamConfigDHCP
                         INTEGER,
                     gponOnuIPParamConfigIPAddr
                         IpAddress,
                     gponOnuIPParamConfigNetmask   
                         IpAddress,
                     gponOnuIPParamConfigGateway 
                         IpAddress, 
                     gponOnuIPParamConfigPriDns 
                         IpAddress,
                     gponOnuIPParamConfigSecDns  
                         IpAddress,
                     gponOnuIPParamConfigRowStatus
                         RowStatus
            }
                 
                 
          gponOnuIPParamConfigIfIndex OBJECT-TYPE
              SYNTAX  INTEGER
              ACCESS  read-only
              STATUS  mandatory

              DESCRIPTION
                      ""
              ::= { gponOnuIPParamConfigEntry 1 }

           gponOnuIPParamConfigDHCP OBJECT-TYPE
              SYNTAX  INTEGER{
                        enable(1),
                        disable(2)
              }
              ACCESS  read-write
              STATUS  mandatory

              DESCRIPTION
                      "1-Enable,2-Disable."
              ::= { gponOnuIPParamConfigEntry 2 }
              
           gponOnuIPParamConfigIPAddr OBJECT-TYPE
              SYNTAX  IpAddress
              ACCESS  read-write
              STATUS  mandatory

              DESCRIPTION
                      "IP Address: A.A.A.A"
              ::= { gponOnuIPParamConfigEntry 3 }              
                           
           gponOnuIPParamConfigNetmask OBJECT-TYPE
              SYNTAX  IpAddress
              ACCESS  read-write
              STATUS  mandatory

              DESCRIPTION
                      "Netmask: A.A.A.A"
              ::= { gponOnuIPParamConfigEntry 4 } 
              
           gponOnuIPParamConfigGateway OBJECT-TYPE
              SYNTAX  IpAddress
              ACCESS  read-write
              STATUS  mandatory

              DESCRIPTION
                      "Gateway: A.A.A.A"
              ::= { gponOnuIPParamConfigEntry 5 }              
              
           gponOnuIPParamConfigPriDns OBJECT-TYPE
              SYNTAX  IpAddress
              ACCESS  read-write
              STATUS  mandatory

              DESCRIPTION
                      "Priority DNS: A.A.A.A"
              ::= { gponOnuIPParamConfigEntry 6 }
              
           gponOnuIPParamConfigSecDns OBJECT-TYPE
              SYNTAX  IpAddress
              ACCESS  read-write
              STATUS  mandatory

              DESCRIPTION
                      "Second DNS: A.A.A.A"
              ::= { gponOnuIPParamConfigEntry 7 }                            
              
           gponOnuIPParamConfigRowStatus OBJECT-TYPE
              SYNTAX  RowStatus
              ACCESS  read-create
              STATUS  mandatory

              DESCRIPTION
                      ""
              ::= { gponOnuIPParamConfigEntry 8 }
              
                                         
--nmsGponUNIPortObj UNI端口任务 OID:1.3.6.1.4.1.3320.10.4

nmsGponUNIPortObj   OBJECT IDENTIFIER ::= { nmsGponMIB 4 }  

-- UNI端口配置表

             onuUniPortConfigTable OBJECT-TYPE
                 SYNTAX  SEQUENCE OF OnuUniPortConfigEntry
                 ACCESS  not-accessible
                 STATUS  mandatory
                 DESCRIPTION
                          "Onu UNI port config table."
                 ::= { nmsGponUNIPortObj 1 }

             onuUniPortConfigEntry OBJECT-TYPE
                 SYNTAX OnuUniPortConfigEntry
                 ACCESS  not-accessible
                 STATUS  mandatory
                 DESCRIPTION
                          "Onu UNI port config table entry."
                 INDEX { onuUniPortConfigDeviceIndex, onuUniPortConfigPortIndex }
             ::= { onuUniPortConfigTable 1 }

             OnuUniPortConfigEntry ::=
                 SEQUENCE {
                     onuUniPortConfigDeviceIndex
                         INTEGER,
                     onuUniPortConfigPortIndex
                         INTEGER,
                     onuUniPortConfigAdminState
                         INTEGER,
                     onuUniPortConfigOperationalState
                         INTEGER,
                     onuUniPortConfigEthernetProfileID
                         INTEGER,
                     onuUniPortConfigOnuVLANTranslationProfileID
                         INTEGER,
                     onuUniPortConfigRowStatus
                         RowStatus,
                     onuUniPortConfigLoopbackDetect
                         INTEGER,
                     onuUniPortConfigMcstOperProfileID
                         INTEGER,
                     onuUniPortConfigMcstStaticProfileID
                         INTEGER,
                     onuUniPortConfigMcstDynamicProfileID
                         INTEGER,
                     onuUniPortConfigPoeAFATmode
                         INTEGER,
                     onuUniPortConfigPoeWorkMode
                         INTEGER  
            }
                 
                 
          onuUniPortConfigDeviceIndex OBJECT-TYPE
              SYNTAX  INTEGER
              ACCESS  read-only
              STATUS  mandatory

              DESCRIPTION
                      ""
              ::= { onuUniPortConfigEntry 1 }


          onuUniPortConfigPortIndex OBJECT-TYPE
              SYNTAX  INTEGER
              ACCESS  read-only
              STATUS  mandatory

              DESCRIPTION
                      ""
              ::= { onuUniPortConfigEntry 2 }

          onuUniPortConfigAdminState OBJECT-TYPE
              SYNTAX  INTEGER{
                               no-shutdown(1),
                               shutdown(2)
                             }
              ACCESS  read-write
              STATUS  mandatory

              DESCRIPTION
                      "1-No shutdown  2-Shutdown "
              ::= { onuUniPortConfigEntry 3 }

          onuUniPortConfigOperationalState OBJECT-TYPE
              SYNTAX  INTEGER{
                               enable(1),
                               disable(2)
                             }
              ACCESS  read-only
              STATUS  mandatory

              DESCRIPTION
                      "1-enable 2-disable"
              ::= { onuUniPortConfigEntry 4 }

          onuUniPortConfigEthernetProfileID OBJECT-TYPE
              SYNTAX  INTEGER
              ACCESS  read-write
              STATUS  mandatory

              DESCRIPTION
                      "It points to the associated Ethernet UNI profile. 0 means cancel profile config. 
                      Default value is 0."
              ::= { onuUniPortConfigEntry 5 }

          onuUniPortConfigOnuVLANTranslationProfileID OBJECT-TYPE
              SYNTAX  INTEGER
              ACCESS  read-write
              STATUS  mandatory

              DESCRIPTION
                      "It stores the profileIndex of the associated ONU VLAN translation profile.0 means cancel
                       profile config. Default value is 0. "
              ::= { onuUniPortConfigEntry 6 }

          onuUniPortConfigRowStatus OBJECT-TYPE
              SYNTAX  RowStatus
              ACCESS  read-create
              STATUS  mandatory

              DESCRIPTION
                      ""
              ::= { onuUniPortConfigEntry 7 }

          onuUniPortConfigLoopbackDetect OBJECT-TYPE
              SYNTAX  INTEGER{
                                enable(1),
                                disable(2)
                              }
              ACCESS  read-write
              STATUS  mandatory

              DESCRIPTION
                      "1-enable 2-disable "
              ::= { onuUniPortConfigEntry 8 }

          onuUniPortConfigMcstOperProfileID OBJECT-TYPE
              SYNTAX  INTEGER
              ACCESS  read-write
              STATUS  mandatory

              DESCRIPTION
                      "It points to the associated onu multicast operation configuration profile.
            0 means cancel profile config."
              ::= { onuUniPortConfigEntry 9 }

          onuUniPortConfigMcstStaticProfileID OBJECT-TYPE
              SYNTAX  INTEGER
              ACCESS  read-write
              STATUS  mandatory

              DESCRIPTION
                      "It points to the associated onu multicast static group configuration profile.
            0 means cancel profile config."
              ::= { onuUniPortConfigEntry 10 }

          onuUniPortConfigMcstDynamicProfileID OBJECT-TYPE
              SYNTAX  INTEGER
              ACCESS  read-write
              STATUS  mandatory

              DESCRIPTION
                      "It points to the associated onu multicast dynamic group configuration profile.
            0 means cancel profile config."

              ::= { onuUniPortConfigEntry 11 }

          onuUniPortConfigPoeAFATmode OBJECT-TYPE
              SYNTAX  INTEGER{
                        af(1),
                        at(2)
                        }
              ACCESS  read-write
              STATUS  mandatory

              DESCRIPTION
                      "1-AF 2-AT"

              ::= { onuUniPortConfigEntry 12 }
           
           onuUniPortConfigPoeWorkMode OBJECT-TYPE
              SYNTAX  INTEGER{
                        disable(1),
                        normal(2),
                        force-on(3)
                        }
              ACCESS  read-write
              STATUS  mandatory

              DESCRIPTION
                      "1-disable 2-normal 3-force-on"

              ::= { onuUniPortConfigEntry 13 }

            
-- UNI端口报文统计表

             onuUniPortStatisticTable OBJECT-TYPE
                 SYNTAX  SEQUENCE OF OnuUniPortStatisticEntry
                 ACCESS  not-accessible
                 STATUS  mandatory
                 DESCRIPTION
                          "Onu UNI port config table."
                 ::= { nmsGponUNIPortObj 2 }

             onuUniPortStatisticEntry OBJECT-TYPE
                 SYNTAX OnuUniPortStatisticEntry
                 ACCESS  not-accessible
                 STATUS  mandatory
                 DESCRIPTION
                          "Onu UNI port config table entry."
                 INDEX { onuUniPortStatisticDeviceIndex, onuUniPortStatisticUniPortIndex }
             ::= { onuUniPortStatisticTable 1 }

             OnuUniPortStatisticEntry ::=
                 SEQUENCE {
                     onuUniPortStatisticDeviceIndex
                         INTEGER,
                     onuUniPortStatisticUniPortIndex
                         INTEGER,
                     onuUniPortStatisticTime
                         Counter64,
                     onuUniPortStatisticRxTotalPackets
                         Counter64,
                     onuUniPortStatisticRxUnicastPackets
                         Counter64,
                     onuUniPortStatisticRxMulticastPackets
                         Counter64,
                     onuUniPortStatisticRxBroadcastPackets
                         Counter64,
                     onuUniPortStatisticRxDiscardedPackets
                         Counter64,
                     onuUniPortStatisticTxTotalPackets
                         Counter64,
                     onuUniPortStatisticTxUnicastPackets
                         Counter64,
                     onuUniPortStatisticTxMulticastPackets
                         Counter64,
                     onuUniPortStatisticTxBroadcastPackets
                         Counter64,
                     onuUniPortStatisticTxDiscardedPackets
                         Counter64,
                     onuUniPortStatisticRxUndersizePackets
                         Counter64,
                     onuUniPortStatisticRxFragments
                         Counter64,
                     onuUniPortStatisticRxJabbers
                         Counter64,
                     onuUniPortStatisticRxPackets64Octets
                         Counter64,
                     onuUniPortStatisticRxPackets65to127Octets
                         Counter64,
                     onuUniPortStatisticRxPackets128to255Octets
                         Counter64,
                     onuUniPortStatisticRxPackets256to511Octets
                         Counter64,
                     onuUniPortStatisticRxPackets512to1023Octets
                         Counter64,
                     onuUniPortStatisticRxPackets1024to1518Octets
                         Counter64,
                     onuUniPortStatisticRxFcsErrors
                         Counter64,
                     onuUniPortStatisticTxFcsErrors
                         Counter64,
                     onuUniPortStatisticTxExcessiveCollisions
                         Counter64,
                     onuUniPortStatisticTxLateCollisions
                         Counter64,
                     onuUniPortStatisticRxPacketsTooLong
                         Counter64,
                     onuUniPortStatisticRxBufferOverflows
                         Counter64,
                     onuUniPortStatisticTxBufferOverflows
                         Counter64,
                     onuUniPortStatisticTxSingleCollisionPackets
                         Counter64,
                     onuUniPortStatisticTxMultipleCollisionsPackets
                         Counter64,
                     onuUniPortStatisticSQEs
                         Counter64,
                     onuUniPortStatisticTxDeferredTransmissio
                         Counter64,
                     onuUniPortStatisticTxInternalMACTransmitError
                         Counter64,
                     onuUniPortStatisticCarrierSenseError
                         Counter64,
                     onuUniPortStatisticRxAlignmentError
                         Counter64,
                     onuUniPortStatisticRxInternalMACReceiveError
                         Counter64,
                     onuUniPortStatisticRxOctets
                         Counter64,
                     onuUniPortStatisticTxOctets
                         Counter64
                     
            }
                 
                 
          onuUniPortStatisticDeviceIndex OBJECT-TYPE
              SYNTAX  INTEGER
              ACCESS  read-only
              STATUS  mandatory

              DESCRIPTION
                      ""
              ::= { onuUniPortStatisticEntry 1 }

          onuUniPortStatisticUniPortIndex OBJECT-TYPE
              SYNTAX  INTEGER
              ACCESS  read-only
              STATUS  mandatory

              DESCRIPTION
                      ""
              ::= { onuUniPortStatisticEntry 2 }


          onuUniPortStatisticTime OBJECT-TYPE
              SYNTAX  Counter64
              ACCESS  read-only
              STATUS  mandatory

              DESCRIPTION
                      "unit： second"
              ::= { onuUniPortStatisticEntry 3 }
              
          onuUniPortStatisticRxTotalPackets OBJECT-TYPE
              SYNTAX  Counter64
              ACCESS  read-only
              STATUS  mandatory

              DESCRIPTION
                      ""
              ::= { onuUniPortStatisticEntry 4 }
              
          onuUniPortStatisticRxUnicastPackets OBJECT-TYPE
              SYNTAX  Counter64
              ACCESS  read-only
              STATUS  mandatory

              DESCRIPTION
                      ""
              ::= { onuUniPortStatisticEntry 5 }

          onuUniPortStatisticRxMulticastPackets OBJECT-TYPE
              SYNTAX  Counter64
              ACCESS  read-only
              STATUS  mandatory

              DESCRIPTION
                      ""
              ::= { onuUniPortStatisticEntry 6 }

          onuUniPortStatisticRxBroadcastPackets OBJECT-TYPE
              SYNTAX  Counter64
              ACCESS  read-only
              STATUS  mandatory

              DESCRIPTION
                      ""
              ::= { onuUniPortStatisticEntry 7 }

          onuUniPortStatisticRxDiscardedPackets OBJECT-TYPE
              SYNTAX  Counter64
              ACCESS  read-only
              STATUS  mandatory

              DESCRIPTION
                      ""
              ::= { onuUniPortStatisticEntry 8 }

          onuUniPortStatisticTxTotalPackets OBJECT-TYPE
              SYNTAX  Counter64
              ACCESS  read-only
              STATUS  mandatory

              DESCRIPTION
                      ""
              ::= { onuUniPortStatisticEntry 9 }

          onuUniPortStatisticTxUnicastPackets OBJECT-TYPE
              SYNTAX  Counter64
              ACCESS  read-only
              STATUS  mandatory

              DESCRIPTION
                      ""
              ::= { onuUniPortStatisticEntry 10 }

          onuUniPortStatisticTxMulticastPackets OBJECT-TYPE
              SYNTAX  Counter64
              ACCESS  read-only
              STATUS  mandatory

              DESCRIPTION
                      ""
              ::= { onuUniPortStatisticEntry 11 }

          onuUniPortStatisticTxBroadcastPackets OBJECT-TYPE
              SYNTAX  Counter64
              ACCESS  read-only
              STATUS  mandatory

              DESCRIPTION
                      ""
              ::= { onuUniPortStatisticEntry 12 }

          onuUniPortStatisticTxDiscardedPackets OBJECT-TYPE
              SYNTAX  Counter64
              ACCESS  read-only
              STATUS  mandatory

              DESCRIPTION
                      ""
              ::= { onuUniPortStatisticEntry 13 }

          onuUniPortStatisticRxUndersizePackets OBJECT-TYPE
              SYNTAX  Counter64
              ACCESS  read-only
              STATUS  mandatory

              DESCRIPTION
                      ""
              ::= { onuUniPortStatisticEntry 14 }

          onuUniPortStatisticRxFragments OBJECT-TYPE
              SYNTAX  Counter64
              ACCESS  read-only
              STATUS  mandatory

              DESCRIPTION
                      ""
              ::= { onuUniPortStatisticEntry 15 }

          onuUniPortStatisticRxJabbers OBJECT-TYPE
              SYNTAX  Counter64
              ACCESS  read-only
              STATUS  mandatory

              DESCRIPTION
                      ""
              ::= { onuUniPortStatisticEntry 16 }

          onuUniPortStatisticRxPackets64Octets OBJECT-TYPE
              SYNTAX  Counter64
              ACCESS  read-only
              STATUS  mandatory

              DESCRIPTION
                      ""
              ::= { onuUniPortStatisticEntry 17 }

          onuUniPortStatisticRxPackets65to127Octets OBJECT-TYPE
              SYNTAX  Counter64
              ACCESS  read-only
              STATUS  mandatory

              DESCRIPTION
                      ""
              ::= { onuUniPortStatisticEntry 18 }

          onuUniPortStatisticRxPackets128to255Octets OBJECT-TYPE
              SYNTAX  Counter64
              ACCESS  read-only
              STATUS  mandatory

              DESCRIPTION
                      ""
              ::= { onuUniPortStatisticEntry 19 }

          onuUniPortStatisticRxPackets256to511Octets OBJECT-TYPE
              SYNTAX  Counter64
              ACCESS  read-only
              STATUS  mandatory

              DESCRIPTION
                      ""
              ::= { onuUniPortStatisticEntry 20 }

          onuUniPortStatisticRxPackets512to1023Octets OBJECT-TYPE
              SYNTAX  Counter64
              ACCESS  read-only
              STATUS  mandatory

              DESCRIPTION
                      ""
              ::= { onuUniPortStatisticEntry 21 }

          onuUniPortStatisticRxPackets1024to1518Octets OBJECT-TYPE
              SYNTAX  Counter64
              ACCESS  read-only
              STATUS  mandatory

              DESCRIPTION
                      ""
              ::= { onuUniPortStatisticEntry 22 }

          onuUniPortStatisticRxFcsErrors OBJECT-TYPE
              SYNTAX  Counter64
              ACCESS  read-only
              STATUS  mandatory

              DESCRIPTION
                      ""
              ::= { onuUniPortStatisticEntry 23 }

          onuUniPortStatisticTxFcsErrors OBJECT-TYPE
              SYNTAX  Counter64
              ACCESS  read-only
              STATUS  mandatory

              DESCRIPTION
                      ""
              ::= { onuUniPortStatisticEntry 24 }

          onuUniPortStatisticTxExcessiveCollisions OBJECT-TYPE
              SYNTAX  Counter64
              ACCESS  read-only
              STATUS  mandatory

              DESCRIPTION
                      ""
              ::= { onuUniPortStatisticEntry 25 }

          onuUniPortStatisticTxLateCollisions OBJECT-TYPE
              SYNTAX  Counter64
              ACCESS  read-only
              STATUS  mandatory

              DESCRIPTION
                      ""
              ::= { onuUniPortStatisticEntry 26 }

          onuUniPortStatisticRxPacketsTooLong OBJECT-TYPE
              SYNTAX  Counter64
              ACCESS  read-only
              STATUS  mandatory

              DESCRIPTION
                      ""
              ::= { onuUniPortStatisticEntry 27 }

          onuUniPortStatisticRxBufferOverflows OBJECT-TYPE
              SYNTAX  Counter64
              ACCESS  read-only
              STATUS  mandatory

              DESCRIPTION
                      ""
              ::= { onuUniPortStatisticEntry 28 }

          onuUniPortStatisticTxBufferOverflows OBJECT-TYPE
              SYNTAX  Counter64
              ACCESS  read-only
              STATUS  mandatory

              DESCRIPTION
                      ""
              ::= { onuUniPortStatisticEntry 29 }

          onuUniPortStatisticTxSingleCollisionPackets OBJECT-TYPE
              SYNTAX  Counter64
              ACCESS  read-only
              STATUS  mandatory

              DESCRIPTION
                      ""
              ::= { onuUniPortStatisticEntry 30 }

          onuUniPortStatisticTxMultipleCollisionsPackets OBJECT-TYPE
              SYNTAX  Counter64
              ACCESS  read-only
              STATUS  mandatory

              DESCRIPTION
                      ""
              ::= { onuUniPortStatisticEntry 31 }

          onuUniPortStatisticSQEs OBJECT-TYPE
              SYNTAX  Counter64
              ACCESS  read-only
              STATUS  mandatory

              DESCRIPTION
                      ""
              ::= { onuUniPortStatisticEntry 32 }

          onuUniPortStatisticTxDeferredTransmissio OBJECT-TYPE
              SYNTAX  Counter64
              ACCESS  read-only
              STATUS  mandatory

              DESCRIPTION
                      ""
              ::= { onuUniPortStatisticEntry 33 }

          onuUniPortStatisticTxInternalMACTransmitError OBJECT-TYPE
              SYNTAX  Counter64
              ACCESS  read-only
              STATUS  mandatory

              DESCRIPTION
                      ""
              ::= { onuUniPortStatisticEntry 34 }

          onuUniPortStatisticCarrierSenseError OBJECT-TYPE
              SYNTAX  Counter64
              ACCESS  read-only
              STATUS  mandatory

              DESCRIPTION
                      ""
              ::= { onuUniPortStatisticEntry 35 }

          onuUniPortStatisticRxAlignmentError OBJECT-TYPE
              SYNTAX  Counter64
              ACCESS  read-only
              STATUS  mandatory

              DESCRIPTION
                      ""
              ::= { onuUniPortStatisticEntry 36 }

          onuUniPortStatisticRxInternalMACReceiveError OBJECT-TYPE
              SYNTAX  Counter64
              ACCESS  read-only
              STATUS  mandatory

              DESCRIPTION
                      ""
              ::= { onuUniPortStatisticEntry 37 }

          onuUniPortStatisticRxOctets OBJECT-TYPE
              SYNTAX  Counter64
              ACCESS  read-only
              STATUS  mandatory

              DESCRIPTION
                      ""
              ::= { onuUniPortStatisticEntry 38 }

          onuUniPortStatisticTxOctets OBJECT-TYPE
              SYNTAX  Counter64
              ACCESS  read-only
              STATUS  mandatory

              DESCRIPTION
                      ""
              ::= { onuUniPortStatisticEntry 39 }


-- UNI端口15min报文统计表

             onuUniPort15MinStatisticTable OBJECT-TYPE
                 SYNTAX  SEQUENCE OF OnuUniPort15MinStatisticEntry
                 ACCESS  not-accessible
                 STATUS  mandatory
                 DESCRIPTION
                          "Onu UNI port 15 minute statistics table."
                 ::= { nmsGponUNIPortObj 3 }

             onuUniPort15MinStatisticEntry OBJECT-TYPE
                 SYNTAX OnuUniPort15MinStatisticEntry
                 ACCESS  not-accessible
                 STATUS  mandatory
                 DESCRIPTION
                          "Onu UNI port 15 minute statistics table entry."
                 INDEX { onuUniPort15MinStatisticDeviceIndex, onuUniPort15MinStatisticUniPortIndex,onuUniPort15MinStatisticIntervalID }
             ::= { onuUniPort15MinStatisticTable 1 }

             OnuUniPort15MinStatisticEntry ::=
                 SEQUENCE {
                     onuUniPort15MinStatisticDeviceIndex
                         INTEGER,
                     onuUniPort15MinStatisticUniPortIndex
                         INTEGER,
                     onuUniPort15MinStatisticIntervalID
                         INTEGER,
                     onuUniPort15MinStatisticRxTotalPackets
                         Counter64,
                     onuUniPort15MinStatisticRxUnicastPackets
                         Counter64,
                     onuUniPort15MinStatisticRxMulticastPackets
                         Counter64,
                     onuUniPort15MinStatisticRxBroadcastPackets
                         Counter64,
                     onuUniPort15MinStatisticRxDiscardedPackets
                         Counter64,
                     onuUniPort15MinStatisticTxTotalPackets
                         Counter64,
                     onuUniPort15MinStatisticTxUnicastPackets
                         Counter64,
                     onuUniPort15MinStatisticTxMulticastPackets
                         Counter64,
                     onuUniPort15MinStatisticTxBroadcastPackets
                         Counter64,
                     onuUniPort15MinStatisticTxDiscardedPackets
                         Counter64,
                     onuUniPort15MinStatisticRxUndersizePackets
                         Counter64,
                     onuUniPort15MinStatisticRxFragments
                         Counter64,
                     onuUniPort15MinStatisticRxJabbers
                         Counter64,
                     onuUniPort15MinStatisticRxPackets64Octets
                         Counter64,
                     onuUniPort15MinStatisticRxPackets65to127Octets
                         Counter64,
                     onuUniPort15MinStatisticRxPackets128to255Octets
                         Counter64,
                     onuUniPort15MinStatisticRxPackets256to511Octets
                         Counter64,
                     onuUniPort15MinStatisticRxPackets512to1023Octets
                         Counter64,
                     onuUniPort15MinStatisticRxPackets1024to1518Octets
                         Counter64,
                     onuUniPort15MinStatisticRxFcsErrors
                         Counter64,
                     onuUniPort15MinStatisticTxFcsErrors
                         Counter64,
                     onuUniPort15MinStatisticTxExcessiveCollisions
                         Counter64,
                     onuUniPort15MinStatisticTxLateCollisions
                         Counter64,
                     onuUniPort15MinStatisticRxPacketsTooLong
                         Counter64,
                     onuUniPort15MinStatisticRxBufferOverflows
                         Counter64,
                     onuUniPort15MinStatisticTxBufferOverflows
                         Counter64,
                     onuUniPort15MinStatisticTxSingleCollisionPackets
                         Counter64,
                     onuUniPort15MinStatisticTxMultipleCollisionsPackets
                         Counter64,
                     onuUniPort15MinStatisticSQEs
                         Counter64,
                     onuUniPort15MinStatisticTxDeferredTransmissio
                         Counter64,
                     onuUniPort15MinStatisticTxInternalMACTransmitError
                         Counter64,
                     onuUniPort15MinStatisticCarrierSenseError
                         Counter64,
                     onuUniPort15MinStatisticRxAlignmentError
                         Counter64,
                     onuUniPort15MinStatisticRxInternalMACReceiveError
                         Counter64,
                     onuUniPort15MinStatisticRxOctets
                         Counter64,
                     onuUniPort15MinStatisticTxOctets
                         Counter64
                     
            }
                 
                 
          onuUniPort15MinStatisticDeviceIndex OBJECT-TYPE
              SYNTAX  INTEGER
              ACCESS  read-only
              STATUS  mandatory

              DESCRIPTION
                      ""
              ::= { onuUniPort15MinStatisticEntry 1 }

          onuUniPort15MinStatisticUniPortIndex OBJECT-TYPE
              SYNTAX  INTEGER
              ACCESS  read-only
              STATUS  mandatory

              DESCRIPTION
                      ""
              ::= { onuUniPort15MinStatisticEntry 2 }

          onuUniPort15MinStatisticIntervalID OBJECT-TYPE
              SYNTAX  INTEGER
              ACCESS  read-only
              STATUS  mandatory

              DESCRIPTION
                      ""
              ::= { onuUniPort15MinStatisticEntry 3 }

          onuUniPort15MinStatisticRxTotalPackets OBJECT-TYPE
              SYNTAX  Counter64
              ACCESS  read-only
              STATUS  mandatory

              DESCRIPTION
                      ""
              ::= { onuUniPort15MinStatisticEntry 4 }

          onuUniPort15MinStatisticRxUnicastPackets OBJECT-TYPE
              SYNTAX  Counter64
              ACCESS  read-only
              STATUS  mandatory

              DESCRIPTION
                      ""
              ::= { onuUniPort15MinStatisticEntry 5 }

          onuUniPort15MinStatisticRxMulticastPackets OBJECT-TYPE
              SYNTAX  Counter64
              ACCESS  read-only
              STATUS  mandatory

              DESCRIPTION
                      ""
              ::= { onuUniPort15MinStatisticEntry 6 }

          onuUniPort15MinStatisticRxBroadcastPackets OBJECT-TYPE
              SYNTAX  Counter64
              ACCESS  read-only
              STATUS  mandatory

              DESCRIPTION
                      ""
              ::= { onuUniPort15MinStatisticEntry 7 }

          onuUniPort15MinStatisticRxDiscardedPackets OBJECT-TYPE
              SYNTAX  Counter64
              ACCESS  read-only
              STATUS  mandatory

              DESCRIPTION
                      ""
              ::= { onuUniPort15MinStatisticEntry 8 }

          onuUniPort15MinStatisticTxTotalPackets OBJECT-TYPE
              SYNTAX  Counter64
              ACCESS  read-only
              STATUS  mandatory

              DESCRIPTION
                      ""
              ::= { onuUniPort15MinStatisticEntry 9 }

          onuUniPort15MinStatisticTxUnicastPackets OBJECT-TYPE
              SYNTAX  Counter64
              ACCESS  read-only
              STATUS  mandatory

              DESCRIPTION
                      ""
              ::= { onuUniPort15MinStatisticEntry 10 }

          onuUniPort15MinStatisticTxMulticastPackets OBJECT-TYPE
              SYNTAX  Counter64
              ACCESS  read-only
              STATUS  mandatory

              DESCRIPTION
                      ""
              ::= { onuUniPort15MinStatisticEntry 11 }

          onuUniPort15MinStatisticTxBroadcastPackets OBJECT-TYPE
              SYNTAX  Counter64
              ACCESS  read-only
              STATUS  mandatory

              DESCRIPTION
                      ""
              ::= { onuUniPort15MinStatisticEntry 12 }

          onuUniPort15MinStatisticTxDiscardedPackets OBJECT-TYPE
              SYNTAX  Counter64
              ACCESS  read-only
              STATUS  mandatory

              DESCRIPTION
                      ""
              ::= { onuUniPort15MinStatisticEntry 13 }

          onuUniPort15MinStatisticRxUndersizePackets OBJECT-TYPE
              SYNTAX  Counter64
              ACCESS  read-only
              STATUS  mandatory

              DESCRIPTION
                      ""
              ::= { onuUniPort15MinStatisticEntry 14 }

          onuUniPort15MinStatisticRxFragments OBJECT-TYPE
              SYNTAX  Counter64
              ACCESS  read-only
              STATUS  mandatory

              DESCRIPTION
                      ""
              ::= { onuUniPort15MinStatisticEntry 15 }

          onuUniPort15MinStatisticRxJabbers OBJECT-TYPE
              SYNTAX  Counter64
              ACCESS  read-only
              STATUS  mandatory

              DESCRIPTION
                      ""
              ::= { onuUniPort15MinStatisticEntry 16 }

          onuUniPort15MinStatisticRxPackets64Octets OBJECT-TYPE
              SYNTAX  Counter64
              ACCESS  read-only
              STATUS  mandatory

              DESCRIPTION
                      ""
              ::= { onuUniPort15MinStatisticEntry 17 }

          onuUniPort15MinStatisticRxPackets65to127Octets OBJECT-TYPE
              SYNTAX  Counter64
              ACCESS  read-only
              STATUS  mandatory

              DESCRIPTION
                      ""
              ::= { onuUniPort15MinStatisticEntry 18 }

          onuUniPort15MinStatisticRxPackets128to255Octets OBJECT-TYPE
              SYNTAX  Counter64
              ACCESS  read-only
              STATUS  mandatory

              DESCRIPTION
                      ""
              ::= { onuUniPort15MinStatisticEntry 19 }

          onuUniPort15MinStatisticRxPackets256to511Octets OBJECT-TYPE
              SYNTAX  Counter64
              ACCESS  read-only
              STATUS  mandatory

              DESCRIPTION
                      ""
              ::= { onuUniPort15MinStatisticEntry 20 }

          onuUniPort15MinStatisticRxPackets512to1023Octets OBJECT-TYPE
              SYNTAX  Counter64
              ACCESS  read-only
              STATUS  mandatory

              DESCRIPTION
                      ""
              ::= { onuUniPort15MinStatisticEntry 21 }

          onuUniPort15MinStatisticRxPackets1024to1518Octets OBJECT-TYPE
              SYNTAX  Counter64
              ACCESS  read-only
              STATUS  mandatory

              DESCRIPTION
                      ""
              ::= { onuUniPort15MinStatisticEntry 22 }
              
          onuUniPort15MinStatisticRxFcsErrors OBJECT-TYPE
              SYNTAX  Counter64
              ACCESS  read-only
              STATUS  mandatory

              DESCRIPTION
                      ""
              ::= { onuUniPort15MinStatisticEntry 23 }
              
          onuUniPort15MinStatisticTxFcsErrors OBJECT-TYPE
              SYNTAX  Counter64
              ACCESS  read-only
              STATUS  mandatory

              DESCRIPTION
                      ""
              ::= { onuUniPort15MinStatisticEntry 24 }
              
          onuUniPort15MinStatisticTxExcessiveCollisions OBJECT-TYPE
              SYNTAX  Counter64
              ACCESS  read-only
              STATUS  mandatory

              DESCRIPTION
                      ""
              ::= { onuUniPort15MinStatisticEntry 25 }
              
          onuUniPort15MinStatisticTxLateCollisions OBJECT-TYPE
              SYNTAX  Counter64
              ACCESS  read-only
              STATUS  mandatory

              DESCRIPTION
                      ""
              ::= { onuUniPort15MinStatisticEntry 26 }
              
          onuUniPort15MinStatisticRxPacketsTooLong OBJECT-TYPE
              SYNTAX  Counter64
              ACCESS  read-only
              STATUS  mandatory

              DESCRIPTION
                      ""
              ::= { onuUniPort15MinStatisticEntry 27 }
              
          onuUniPort15MinStatisticRxBufferOverflows OBJECT-TYPE
              SYNTAX  Counter64
              ACCESS  read-only
              STATUS  mandatory

              DESCRIPTION
                      ""
              ::= { onuUniPort15MinStatisticEntry 28 }
              
          onuUniPort15MinStatisticTxBufferOverflows OBJECT-TYPE
              SYNTAX  Counter64
              ACCESS  read-only
              STATUS  mandatory

              DESCRIPTION
                      ""
              ::= { onuUniPort15MinStatisticEntry 29 }
              
          onuUniPort15MinStatisticTxSingleCollisionPackets OBJECT-TYPE
              SYNTAX  Counter64
              ACCESS  read-only
              STATUS  mandatory

              DESCRIPTION
                      ""
              ::= { onuUniPort15MinStatisticEntry 30 }
              
          onuUniPort15MinStatisticTxMultipleCollisionsPackets OBJECT-TYPE
              SYNTAX  Counter64
              ACCESS  read-only
              STATUS  mandatory

              DESCRIPTION
                      ""
              ::= { onuUniPort15MinStatisticEntry 31 }
              
          onuUniPort15MinStatisticSQEs OBJECT-TYPE
              SYNTAX  Counter64
              ACCESS  read-only
              STATUS  mandatory

              DESCRIPTION
                      ""
              ::= { onuUniPort15MinStatisticEntry 32 }
              
          onuUniPort15MinStatisticTxDeferredTransmissio OBJECT-TYPE
              SYNTAX  Counter64
              ACCESS  read-only
              STATUS  mandatory

              DESCRIPTION
                      ""
              ::= { onuUniPort15MinStatisticEntry 33 }
              
          onuUniPort15MinStatisticTxInternalMACTransmitError OBJECT-TYPE
              SYNTAX  Counter64
              ACCESS  read-only
              STATUS  mandatory

              DESCRIPTION
                      ""
              ::= { onuUniPort15MinStatisticEntry 34 }
              
          onuUniPort15MinStatisticCarrierSenseError OBJECT-TYPE
              SYNTAX  Counter64
              ACCESS  read-only
              STATUS  mandatory

              DESCRIPTION
                      ""
              ::= { onuUniPort15MinStatisticEntry 35 }
              
          onuUniPort15MinStatisticRxAlignmentError OBJECT-TYPE
              SYNTAX  Counter64
              ACCESS  read-only
              STATUS  mandatory

              DESCRIPTION
                      ""
              ::= { onuUniPort15MinStatisticEntry 36 }
              
          onuUniPort15MinStatisticRxInternalMACReceiveError OBJECT-TYPE
              SYNTAX  Counter64
              ACCESS  read-only
              STATUS  mandatory

              DESCRIPTION
                      ""
              ::= { onuUniPort15MinStatisticEntry 37 }
              
          onuUniPort15MinStatisticRxOctets OBJECT-TYPE
              SYNTAX  Counter64
              ACCESS  read-only
              STATUS  mandatory

              DESCRIPTION
                      ""
              ::= { onuUniPort15MinStatisticEntry 38 }
              
          onuUniPort15MinStatisticTxOctets OBJECT-TYPE
              SYNTAX  Counter64
              ACCESS  read-only
              STATUS  mandatory

              DESCRIPTION
                      ""
              ::= { onuUniPort15MinStatisticEntry 39 }                 
                 
                                            
-- Onu Uni Port Alarm陷阱

    onuUniPortAlarmTrap OBJECT IDENTIFIER
                                ::= { nmsGponUNIPortObj 4 }


        onuUniPortLoopbackDetectResult OBJECT-TYPE
              SYNTAX  INTEGER{
                              alarm(1),
                              clear(2)
            }
              ACCESS  read-only
              STATUS  mandatory

              DESCRIPTION
                      ""
              ::= { onuUniPortAlarmTrap 1 }


        onuUniPortLoopbackDetectNotification NOTIFICATION-TYPE
            OBJECTS {
                       ifIndex,
                       ifDescr,
                       onuSerialNum,
                       uniPort,
                       statusChange
            }
            STATUS      current
            DESCRIPTION
            "The agent generates this notification when ONU uni port loopback detected ."
            ::= { onuUniPortAlarmTrap 2 }  
                                      
                                      
        onuUniPortState OBJECT-TYPE
              SYNTAX  INTEGER{
                              down(1),
                              up(2)
            }
              ACCESS  read-only
              STATUS  mandatory

              DESCRIPTION
                      ""
              ::= { onuUniPortAlarmTrap 3 }


        onuUniPortStateNotification NOTIFICATION-TYPE
            OBJECTS {
                       ifIndex,
                       ifDescr,
                       onuSerialNum,
                       uniPort,
                       statusChange
            }
            STATUS      current
            DESCRIPTION
            "The agent generates this notification when ONU uni port state changed ."
            ::= { onuUniPortAlarmTrap 4 }

 
 -- UNI端口POE状态表

             onuUniPortPoeStatusTable OBJECT-TYPE
                 SYNTAX  SEQUENCE OF OnuUniPortPoeStatusEntry
                 ACCESS  not-accessible
                 STATUS  mandatory
                 DESCRIPTION
                          "Onu UNI port status table."
                 ::= { nmsGponUNIPortObj 5 }

             onuUniPortPoeStatusEntry OBJECT-TYPE
                 SYNTAX OnuUniPortPoeStatusEntry
                 ACCESS  not-accessible
                 STATUS  mandatory
                 DESCRIPTION
                          "Onu UNI port status table entry."
                 INDEX { onuUniPortPoeStatusDeviceIndex, onuUniPortPoeStatusPortIndex }
             ::= { onuUniPortPoeStatusTable 1 }

             OnuUniPortPoeStatusEntry ::=
                 SEQUENCE {
                     onuUniPortPoeStatusDeviceIndex
                         INTEGER,
                     onuUniPortPoeStatusPortIndex
                         INTEGER,
                     onuUniPortPoeStatusPowerStatus
                         INTEGER,              
                     onuUniPortPoeStatusDetectResult
                         INTEGER,             
                     onuUniPortPoeStatusClassCurrent
                         INTEGER,             
                     onuUniPortPoeStatusClassResult
                         INTEGER,              
                     onuUniPortPoeStatusPDRequestPower
                         INTEGER,          
                     onuUniPortPoeStatusPollPortCurrent
                         INTEGER,          
                     onuUniPortPoeStatusPollPortVoltage
                         INTEGER,          
                     onuUniPortPoeStatusPollTemperature
                         INTEGER,
                     onuUniPortPoeStatusItuPoeOperStatus
                         INTEGER,
                     onuUniPortPoeStatusItuPowerPairPinout
                         INTEGER,
                     onuUniPortPoeStatusItuPowerDectionStatus
                         INTEGER,
                     onuUniPortPoeStatusItuPowerClassStatus
                         INTEGER,
                     onuUniPortPoeStatusItuPowerPri
                         INTEGER,
                     onuUniPortPoeStatusItuPseClassCtrl
                         INTEGER,
                     onuUniPortPoeStatusItuPoeCapability
                         BITS,
                     onuUniPortPoeStatusItuInvalidSigCount
                         INTEGER,
                     onuUniPortPoeStatusItuPowerDeniedCount
                         INTEGER,
                     onuUniPortPoeStatusItuOverloadCount
                         INTEGER,
                     onuUniPortPoeStatusItuShortCount
                         INTEGER,
                     onuUniPortPoeStatusItuMpsAbsentCount
                         INTEGER,
                     onuUniPortPoeStatusItuCurrentPowerConsumption
                         INTEGER
                 }
 
 
          onuUniPortPoeStatusDeviceIndex OBJECT-TYPE
              SYNTAX  INTEGER
              ACCESS  read-only
              STATUS  mandatory

              DESCRIPTION
                      ""
              ::= { onuUniPortPoeStatusEntry 1 }

          onuUniPortPoeStatusPortIndex OBJECT-TYPE
              SYNTAX  INTEGER
              ACCESS  read-only
              STATUS  mandatory

              DESCRIPTION
                      ""                       
              ::= { onuUniPortPoeStatusEntry 2 }
              
           onuUniPortPoeStatusPowerStatus OBJECT-TYPE
              SYNTAX  INTEGER
              ACCESS  read-only
              STATUS  mandatory

              DESCRIPTION
                      ""
              ::= { onuUniPortPoeStatusEntry 3 }

            onuUniPortPoeStatusDetectResult OBJECT-TYPE
              SYNTAX  INTEGER
              ACCESS  read-only
              STATUS  mandatory

              DESCRIPTION
                      ""
              ::= { onuUniPortPoeStatusEntry 4 }

            onuUniPortPoeStatusClassCurrent OBJECT-TYPE
              SYNTAX  INTEGER
              ACCESS  read-only
              STATUS  mandatory

              DESCRIPTION
                      ""
              ::= { onuUniPortPoeStatusEntry 5 }

            onuUniPortPoeStatusClassResult OBJECT-TYPE
              SYNTAX  INTEGER
              ACCESS  read-only
              STATUS  mandatory

              DESCRIPTION
                      ""
              ::= { onuUniPortPoeStatusEntry 6 }

            onuUniPortPoeStatusPDRequestPower OBJECT-TYPE
              SYNTAX  INTEGER
              ACCESS  read-only
              STATUS  mandatory

              DESCRIPTION
                      ""
              ::= { onuUniPortPoeStatusEntry 7 }

            onuUniPortPoeStatusPollPortCurrent OBJECT-TYPE
              SYNTAX  INTEGER
              ACCESS  read-only
              STATUS  mandatory

              DESCRIPTION
                      ""
              ::= { onuUniPortPoeStatusEntry 8 }

            onuUniPortPoeStatusPollPortVoltage OBJECT-TYPE
              SYNTAX  INTEGER
              ACCESS  read-only
              STATUS  mandatory

              DESCRIPTION
                      ""
              ::= { onuUniPortPoeStatusEntry 9 }

            onuUniPortPoeStatusPollTemperature OBJECT-TYPE
              SYNTAX  INTEGER
              ACCESS  read-only
              STATUS  mandatory

              DESCRIPTION
                      ""
              ::= { onuUniPortPoeStatusEntry 10 }     
            
            onuUniPortPoeStatusItuPoeOperStatus OBJECT-TYPE
              SYNTAX  INTEGER{
                              up(1),
                              down(2)
                            }
              ACCESS  read-only
              STATUS  mandatory

              DESCRIPTION
                      ""
              ::= { onuUniPortPoeStatusEntry 11 }

            onuUniPortPoeStatusItuPowerPairPinout OBJECT-TYPE
              SYNTAX  INTEGER{
                              none(0),
                              signal(1),
                              spare(2)
                              }
              ACCESS  read-only
              STATUS  mandatory

              DESCRIPTION
                      ""
              ::= { onuUniPortPoeStatusEntry 12 }

            onuUniPortPoeStatusItuPowerDectionStatus OBJECT-TYPE
              SYNTAX  INTEGER{
                                pse-disable(0),
                                pse-searching(1),
                                pse-dilvering-Power(2),
                                pse-test-mode(3),
                                pse-Fault-Detected(4),
                                pse-implementation-specific-fault-detected(5)
                              }
              ACCESS  read-only
              STATUS  mandatory

              DESCRIPTION
                      ""
              ::= { onuUniPortPoeStatusEntry 13 }

            onuUniPortPoeStatusItuPowerClassStatus OBJECT-TYPE
              SYNTAX  INTEGER{
                                class-0-PD(0),
                                class-1-PD(1),
                                class-2-PD(2),
                                class-3-PD(3),
                                class-4-PD(4),
                                undefined-or-feature-not-supported(255)
                              }
              ACCESS  read-only
              STATUS  mandatory

              DESCRIPTION
                      ""
              ::= { onuUniPortPoeStatusEntry 14 }

            onuUniPortPoeStatusItuPowerPri OBJECT-TYPE
              SYNTAX  INTEGER{
                                none(0),
                                critical(1),
                                high(2),
                                low(3)
                            }
              ACCESS  read-only
              STATUS  mandatory

              DESCRIPTION
                      ""
              ::= { onuUniPortPoeStatusEntry 15 }

            onuUniPortPoeStatusItuPseClassCtrl OBJECT-TYPE
              SYNTAX  INTEGER{
                                class-0(0),
                                class-1(1),
                                class-2(2),
                                class-3(3),
                                class-4(4),
                                default(255)
                            }
              ACCESS  read-only
              STATUS  mandatory

              DESCRIPTION
                      "Power feed enabled level"
              ::= { onuUniPortPoeStatusEntry 16 }   
              
            onuUniPortPoeStatusItuPoeCapability OBJECT-TYPE
              SYNTAX  BITS {
                        support-power-pair-pinout-ctrl(7)
                        }
              ACCESS  read-only
              STATUS  mandatory

              DESCRIPTION
                      ""
              ::= { onuUniPortPoeStatusEntry 17 }

            onuUniPortPoeStatusItuInvalidSigCount OBJECT-TYPE
              SYNTAX  INTEGER
              ACCESS  read-only
              STATUS  mandatory

              DESCRIPTION
                      ""
              ::= { onuUniPortPoeStatusEntry 18 }

            onuUniPortPoeStatusItuPowerDeniedCount OBJECT-TYPE
              SYNTAX  INTEGER
              ACCESS  read-only
              STATUS  mandatory

              DESCRIPTION
                      ""
              ::= { onuUniPortPoeStatusEntry 19 }

            onuUniPortPoeStatusItuOverloadCount OBJECT-TYPE
              SYNTAX  INTEGER
              ACCESS  read-only
              STATUS  mandatory

              DESCRIPTION
                      ""
              ::= { onuUniPortPoeStatusEntry 20 }

            onuUniPortPoeStatusItuShortCount OBJECT-TYPE
              SYNTAX  INTEGER
              ACCESS  read-only
              STATUS  mandatory

              DESCRIPTION
                      ""
              ::= { onuUniPortPoeStatusEntry 21 }

            onuUniPortPoeStatusItuMpsAbsentCount OBJECT-TYPE
              SYNTAX  INTEGER
              ACCESS  read-only
              STATUS  mandatory

              DESCRIPTION
                      ""
              ::= { onuUniPortPoeStatusEntry 22 } 
              
            onuUniPortPoeStatusItuCurrentPowerConsumption OBJECT-TYPE
              SYNTAX  INTEGER
              UNITS   "mW"
              ACCESS  read-only
              STATUS  mandatory

              DESCRIPTION
                      "Actual power being provided by this port(mW)."
              ::= { onuUniPortPoeStatusEntry 23 }
              
-- UNI/VEIP/Ip-Host端口通用配置表

             onuCommonPortConfigTable OBJECT-TYPE
                 SYNTAX  SEQUENCE OF OnuCommonPortConfigEntry
                 ACCESS  not-accessible
                 STATUS  mandatory
                 DESCRIPTION
                          "Onu UNI port config table."
                 ::= { nmsGponUNIPortObj 6 }

             onuCommonPortConfigEntry OBJECT-TYPE
                 SYNTAX OnuCommonPortConfigEntry
                 ACCESS  not-accessible
                 STATUS  mandatory
                 DESCRIPTION
                          "Onu UNI port config table entry."
                 INDEX { onuCommonPortConfigDeviceIndex, onuCommonPortConfigPortIndex }
             ::= { onuCommonPortConfigTable 1 }

             OnuCommonPortConfigEntry ::=
                 SEQUENCE {
                     onuCommonPortConfigDeviceIndex
                         INTEGER,
                     onuCommonPortConfigPortIndex
                         INTEGER,
                     onuCommonPortConfigAdminState
                         INTEGER,
                     onuCommonPortConfigOnuVLANTranslationProfileID
                         INTEGER,
                     onuCommonPortConfigMcstOperProfileID
                         INTEGER,
                     onuCommonPortConfigMcstStaticProfileID
                         INTEGER,
                     onuCommonPortConfigMcstDynamicProfileID
                         INTEGER,
                     onuCommonPortConfigRowStatus
                         RowStatus
            }
                 
                 
          onuCommonPortConfigDeviceIndex OBJECT-TYPE
              SYNTAX  INTEGER
              ACCESS  read-only
              STATUS  mandatory

              DESCRIPTION
                      ""
              ::= { onuCommonPortConfigEntry 1 }


          onuCommonPortConfigPortIndex OBJECT-TYPE
              SYNTAX  INTEGER
              ACCESS  read-only
              STATUS  mandatory

              DESCRIPTION
                      "PortIndex consists of port_type and port_id:
                      PortIndex = (port_type << 8) | port_id
                      port_type define:
                      ethuni    0x00
                      veip      0x02
                      iphost    0x04 "
              ::= { onuCommonPortConfigEntry 2 }

          onuCommonPortConfigAdminState OBJECT-TYPE
              SYNTAX  INTEGER{
                               no-shutdown(1),
                               shutdown(2)
                             }
              ACCESS  read-write
              STATUS  mandatory

              DESCRIPTION
                      "1-No shutdown  2-Shutdown "
              ::= { onuCommonPortConfigEntry 3 }

          onuCommonPortConfigOnuVLANTranslationProfileID OBJECT-TYPE
              SYNTAX  INTEGER
              ACCESS  read-write
              STATUS  mandatory

              DESCRIPTION
                      "It stores the profileIndex of the associated ONU VLAN translation profile.0 means cancel
                       profile config. Default value is 0. "
              ::= { onuCommonPortConfigEntry 4 }

          onuCommonPortConfigMcstOperProfileID OBJECT-TYPE
              SYNTAX  INTEGER
              ACCESS  read-write
              STATUS  mandatory

              DESCRIPTION
                      "It points to the associated onu multicast operation configuration profile.
            0 means cancel profile config."
              ::= { onuCommonPortConfigEntry 5 }

          onuCommonPortConfigMcstStaticProfileID OBJECT-TYPE
              SYNTAX  INTEGER
              ACCESS  read-write
              STATUS  mandatory

              DESCRIPTION
                      "It points to the associated onu multicast static group configuration profile.
            0 means cancel profile config."
              ::= { onuCommonPortConfigEntry 6 }

          onuCommonPortConfigMcstDynamicProfileID OBJECT-TYPE
              SYNTAX  INTEGER
              ACCESS  read-write
              STATUS  mandatory

              DESCRIPTION
                      "It points to the associated onu multicast dynamic group configuration profile.
            0 means cancel profile config."

              ::= { onuCommonPortConfigEntry 7 }
              
          onuCommonPortConfigRowStatus OBJECT-TYPE
              SYNTAX  RowStatus
              ACCESS  read-create
              STATUS  mandatory

              DESCRIPTION
                      ""
              ::= { onuCommonPortConfigEntry 8 }  
              
-- VEIP端口配置表

             onuVEIPPortConfigTable OBJECT-TYPE
                 SYNTAX  SEQUENCE OF OnuVEIPPortConfigEntry
                 ACCESS  not-accessible
                 STATUS  mandatory
                 DESCRIPTION
                          "Onu VEIP port config table."
                 ::= { nmsGponUNIPortObj 7 }

             onuVEIPPortConfigEntry OBJECT-TYPE
                 SYNTAX OnuVEIPPortConfigEntry
                 ACCESS  not-accessible
                 STATUS  mandatory
                 DESCRIPTION
                          "Onu VEIP port config table entry."
                 INDEX { onuVEIPPortConfigDeviceIndex, onuVEIPPortConfigPortIndex }
             ::= { onuVEIPPortConfigTable 1 }

             OnuVEIPPortConfigEntry ::=
                 SEQUENCE {
                     onuVEIPPortConfigDeviceIndex
                         INTEGER,
                     onuVEIPPortConfigPortIndex
                         INTEGER,
                     onuVEIPPortConfigOnuVEIPProfileID
                         INTEGER,
                     onuVEIPPortConfigRowStatus
                         RowStatus
            }
                 
                 
          onuVEIPPortConfigDeviceIndex OBJECT-TYPE
              SYNTAX  INTEGER
              ACCESS  read-only
              STATUS  mandatory

              DESCRIPTION
                      ""
              ::= { onuVEIPPortConfigEntry 1 }


          onuVEIPPortConfigPortIndex OBJECT-TYPE
              SYNTAX  INTEGER
              ACCESS  read-only
              STATUS  mandatory

              DESCRIPTION
                      ""
              ::= { onuVEIPPortConfigEntry 2 }

          onuVEIPPortConfigOnuVEIPProfileID OBJECT-TYPE
              SYNTAX  INTEGER
              ACCESS  read-write
              STATUS  mandatory

              DESCRIPTION
                      "It points to the associated onu VEIP configuration profile.
            0 means cancel profile config."
              ::= { onuVEIPPortConfigEntry 3 }
             
          onuVEIPPortConfigRowStatus OBJECT-TYPE
              SYNTAX  RowStatus
              ACCESS  read-create
              STATUS  mandatory

              DESCRIPTION
                      ""
              ::= { onuVEIPPortConfigEntry 4 }
              
-- ONU IP Host配置 
 
             onuIPHostParamConfigTable OBJECT-TYPE
                 SYNTAX  SEQUENCE OF OnuIPHostParamConfigEntry
                 ACCESS  not-accessible
                 STATUS  mandatory
                 DESCRIPTION
                          "Onu IP Host config table."
                 ::= { nmsGponUNIPortObj 8 }
 
             onuIPHostParamConfigEntry OBJECT-TYPE
                 SYNTAX OnuIPHostParamConfigEntry
                 ACCESS  not-accessible
                 STATUS  mandatory
                 DESCRIPTION
                          "Onu IP Host config table entry."
                 INDEX { onuIPHostParamConfigDeviceIndex, onuIPHostParamConfigPortIndex }
                 ::= { onuIPHostParamConfigTable 1 }

             OnuIPHostParamConfigEntry ::=
                 SEQUENCE {
                     onuIPHostParamConfigDeviceIndex
                         INTEGER,       
                     onuIPHostParamConfigPortIndex
                         INTEGER,
                     onuIPHostParamConfigDHCP
                         INTEGER,
                     onuIPHostParamConfigIPAddr
                         IpAddress,
                     onuIPHostParamConfigNetmask   
                         IpAddress,
                     onuIPHostParamConfigGateway 
                         IpAddress, 
                     onuIPHostParamConfigPriDns 
                         IpAddress,
                     onuIPHostParamConfigSecDns  
                         IpAddress,
                     onuIPHostParamConfigRowStatus
                         RowStatus,
                     onuIPHostParamConfigOption
                         INTEGER
            }
                 
                 
          onuIPHostParamConfigDeviceIndex OBJECT-TYPE
              SYNTAX  INTEGER
              ACCESS  read-only
              STATUS  mandatory

              DESCRIPTION
                      ""
              ::= { onuIPHostParamConfigEntry 1 }   
              
          onuIPHostParamConfigPortIndex OBJECT-TYPE
              SYNTAX  INTEGER
              ACCESS  read-only
              STATUS  mandatory

              DESCRIPTION
                      ""
              ::= { onuIPHostParamConfigEntry 2 }

           onuIPHostParamConfigDHCP OBJECT-TYPE
              SYNTAX  INTEGER{
                        enable(1),
                        disable(2)
              }
              ACCESS  read-write
              STATUS  mandatory

              DESCRIPTION
                      "1-Enable,2-Disable."
              ::= { onuIPHostParamConfigEntry 3 }
              
           onuIPHostParamConfigIPAddr OBJECT-TYPE
              SYNTAX  IpAddress
              ACCESS  read-write
              STATUS  mandatory

              DESCRIPTION
                      "IP Address: A.A.A.A"
              ::= { onuIPHostParamConfigEntry 4 }              
                           
           onuIPHostParamConfigNetmask OBJECT-TYPE
              SYNTAX  IpAddress
              ACCESS  read-write
              STATUS  mandatory

              DESCRIPTION
                      "Netmask: A.A.A.A"
              ::= { onuIPHostParamConfigEntry 5 } 
              
           onuIPHostParamConfigGateway OBJECT-TYPE
              SYNTAX  IpAddress
              ACCESS  read-write
              STATUS  mandatory

              DESCRIPTION
                      "Gateway: A.A.A.A"
              ::= { onuIPHostParamConfigEntry 6 }              
              
           onuIPHostParamConfigPriDns OBJECT-TYPE
              SYNTAX  IpAddress
              ACCESS  read-write
              STATUS  mandatory

              DESCRIPTION
                      "Priority DNS: A.A.A.A"
              ::= { onuIPHostParamConfigEntry 7 }
              
           onuIPHostParamConfigSecDns OBJECT-TYPE
              SYNTAX  IpAddress
              ACCESS  read-write
              STATUS  mandatory

              DESCRIPTION
                      "Second DNS: A.A.A.A"
              ::= { onuIPHostParamConfigEntry 8 }                            
              
           onuIPHostParamConfigRowStatus OBJECT-TYPE
              SYNTAX  RowStatus
              ACCESS  read-create
              STATUS  mandatory

              DESCRIPTION
                      ""
              ::= { onuIPHostParamConfigEntry 9 }

           onuIPHostParamConfigOption OBJECT-TYPE
              SYNTAX  INTEGER
              ACCESS  read-write
              STATUS  mandatory

              DESCRIPTION
                      "IP-host IP options, config bit map:
                      0x01      Enable DHCP
                      0x02      Respond to pings
                      0x04      Respond to traceroute messages
                      0x08      Enable IP stack
                      0xFFFF    Not config IP options"
              ::= { onuIPHostParamConfigEntry 10 }

-- UNI/VEIP端口状态表

             onuCommonPortStateTable OBJECT-TYPE
                 SYNTAX  SEQUENCE OF OnuCommonPortStateEntry
                 ACCESS  not-accessible
                 STATUS  mandatory
                 DESCRIPTION
                          "Onu Uni port state table."
                 ::= { nmsGponUNIPortObj 9 }

             onuCommonPortStateEntry OBJECT-TYPE
                 SYNTAX OnuCommonPortStateEntry
                 ACCESS  not-accessible
                 STATUS  mandatory
                 DESCRIPTION
                          "Onu Uni port state entry."
                 INDEX { onuCommonPortStateDeviceIndex, onuCommonPortStatePortIndex }
             ::= { onuCommonPortStateTable 1 }

             OnuCommonPortStateEntry ::=
                 SEQUENCE {
                     onuCommonPortStateDeviceIndex
                         INTEGER,
                     onuCommonPortStatePortIndex
                         INTEGER,
                     onuCommonPortStateOperationalState
                         INTEGER,
            }
                 
                 
          onuCommonPortStateDeviceIndex OBJECT-TYPE
              SYNTAX  INTEGER
              ACCESS  read-only
              STATUS  mandatory

              DESCRIPTION
                      ""
              ::= { onuCommonPortStateEntry 1 }


          onuCommonPortStatePortIndex OBJECT-TYPE
              SYNTAX  INTEGER
              ACCESS  read-only
              STATUS  mandatory

              DESCRIPTION
                      "PortIndex consists of port_type and port_id:
                      PortIndex = (port_type << 8) | port_id
                      port_type define:
                      ethuni    0x00
                      veip      0x02
                      iphost    0x04 "
              ::= { onuCommonPortStateEntry 2 }

          onuCommonPortStateOperationalState OBJECT-TYPE   
              SYNTAX  INTEGER{
                               enable(1),
                               disable(2)
                             }
              ACCESS  read-only
              STATUS  mandatory

              DESCRIPTION
                      "1-enable 2-disable"
              ::= { onuCommonPortStateEntry 3 }

-- ONU IP Host状态表 
 
             onuIPHostStateTable OBJECT-TYPE
                 SYNTAX  SEQUENCE OF OnuIPHostStateEntry
                 ACCESS  not-accessible
                 STATUS  mandatory
                 DESCRIPTION
                          "Onu IP Host state table."
                 ::= { nmsGponUNIPortObj 10 }
 
             onuIPHostStateEntry OBJECT-TYPE
                 SYNTAX OnuIPHostStateEntry
                 ACCESS  not-accessible
                 STATUS  mandatory
                 DESCRIPTION
                          "Onu IP Host config table entry."
                 INDEX { onuIPHostStateDeviceIndex, onuIPHostStatePortIndex }
                 ::= { onuIPHostStateTable 1 }

             OnuIPHostStateEntry ::=
                 SEQUENCE {
                     onuIPHostStateDeviceIndex
                         INTEGER,       
                     onuIPHostStatePortIndex
                         INTEGER,
                     onuIPHostStateMacAddr
                         MacAddress,
                     onuIPHostStateOnuId
                         OCTET STRING,
                     onuIPHostStateConfigOption
                         BITS,
                     onuIPHostStateConfigIPAddr
                         IpAddress,
                     onuIPHostStateConfigNetmask
                         IpAddress,
                     onuIPHostStateConfigGateway
                         IpAddress, 
                     onuIPHostStateConfigPriDns
                         IpAddress,
                     onuIPHostStateConfigSecDns
                         IpAddress,
                     onuIPHostStateCurrentIPAddr
                         IpAddress,
                     onuIPHostStateCurrentNetmask
                         IpAddress,
                     onuIPHostStateCurrentGateway
                         IpAddress, 
                     onuIPHostStateCurrentPriDns
                         IpAddress,
                     onuIPHostStateCurrentSecDns
                         IpAddress,
                     onuIPHostStateCurrentDomainName
                         OCTET STRING,
                     onuIPHostStateCurrentHostName
                         OCTET STRING
            }
                 
                 
          onuIPHostStateDeviceIndex OBJECT-TYPE
              SYNTAX  INTEGER
              ACCESS  read-only
              STATUS  mandatory

              DESCRIPTION
                      ""
              ::= { onuIPHostStateEntry 1 }   
              
          onuIPHostStatePortIndex OBJECT-TYPE
              SYNTAX  INTEGER
              ACCESS  read-only
              STATUS  mandatory

              DESCRIPTION
                      ""
              ::= { onuIPHostStateEntry 2 }

           onuIPHostStateMacAddr OBJECT-TYPE
              SYNTAX  MacAddress
              ACCESS  read-only
              STATUS  mandatory
              
              DESCRIPTION
                      "Mac address of the IP host"
              ::= { onuIPHostStateEntry 3 }

           onuIPHostStateOnuId OBJECT-TYPE
              SYNTAX  OCTET STRING (SIZE (0..25))
              ACCESS  read-only
              STATUS  mandatory
              
              DESCRIPTION
                      "ONU identifier of the IP host"
              ::= { onuIPHostStateEntry 4 }

           onuIPHostStateConfigOption OBJECT-TYPE
              SYNTAX  BITS{
                        ip-stack(4),
                        trace-route(5),
                        ping(6),
                        dhcp(7)
              }
              ACCESS  read-only
              STATUS  mandatory
              
              DESCRIPTION
                      "IP-host IP options, config bit map:
                      0x01      Enable DHCP
                      0x02      Respond to pings
                      0x04      Respond to traceroute messages
                      0x08      Enable IP stack"
              ::= { onuIPHostStateEntry 5 }
              
           onuIPHostStateConfigIPAddr OBJECT-TYPE
              SYNTAX  IpAddress
              ACCESS  read-only
              STATUS  mandatory
              
              DESCRIPTION
                      "IP Address: A.A.A.A"
              ::= { onuIPHostStateEntry 6 }

           onuIPHostStateConfigNetmask OBJECT-TYPE
              SYNTAX  IpAddress
              ACCESS  read-only
              STATUS  mandatory
              
              DESCRIPTION
                      "Netmask: A.A.A.A"
              ::= { onuIPHostStateEntry 7 }

           onuIPHostStateConfigGateway OBJECT-TYPE
              SYNTAX  IpAddress
              ACCESS  read-only
              STATUS  mandatory
              
              DESCRIPTION
                      "Gateway: A.A.A.A"
              ::= { onuIPHostStateEntry 8 }

           onuIPHostStateConfigPriDns OBJECT-TYPE
              SYNTAX  IpAddress
              ACCESS  read-only
              STATUS  mandatory
              
              DESCRIPTION
                      "Primary DNS: A.A.A.A"
              ::= { onuIPHostStateEntry 9 }

           onuIPHostStateConfigSecDns OBJECT-TYPE
              SYNTAX  IpAddress
              ACCESS  read-only
              STATUS  mandatory
              
              DESCRIPTION
                      "Secondary DNS: A.A.A.A"
              ::= { onuIPHostStateEntry 10 }

           onuIPHostStateCurrentIPAddr OBJECT-TYPE
              SYNTAX  IpAddress
              ACCESS  read-only
              STATUS  mandatory
              
              DESCRIPTION
                      "Current Using IP Address: A.A.A.A"
              ::= { onuIPHostStateEntry 11 }

           onuIPHostStateCurrentNetmask OBJECT-TYPE
              SYNTAX  IpAddress
              ACCESS  read-only
              STATUS  mandatory
              
              DESCRIPTION
                      "Current Using Netmask: A.A.A.A"
              ::= { onuIPHostStateEntry 12 }

           onuIPHostStateCurrentGateway OBJECT-TYPE
              SYNTAX  IpAddress
              ACCESS  read-only
              STATUS  mandatory
              
              DESCRIPTION
                      "Current Using Gateway: A.A.A.A"
              ::= { onuIPHostStateEntry 13 }

           onuIPHostStateCurrentPriDns OBJECT-TYPE
              SYNTAX  IpAddress
              ACCESS  read-only
              STATUS  mandatory
              
              DESCRIPTION
                      "Current Using Primary DNS: A.A.A.A"
              ::= { onuIPHostStateEntry 14 }

           onuIPHostStateCurrentSecDns OBJECT-TYPE
              SYNTAX  IpAddress
              ACCESS  read-only
              STATUS  mandatory
              
              DESCRIPTION
                      "Current Using Secondary DNS: A.A.A.A"
              ::= { onuIPHostStateEntry 15 }

           onuIPHostStateCurrentDomainName OBJECT-TYPE
              SYNTAX  OCTET STRING (SIZE (0..25))
              ACCESS  read-only
              STATUS  mandatory
              
              DESCRIPTION
                      "Domain name assigned by DHCP of IP host"
              ::= { onuIPHostStateEntry 16 }

           onuIPHostStateCurrentHostName OBJECT-TYPE
              SYNTAX  OCTET STRING (SIZE (0..25))
              ACCESS  read-only
              STATUS  mandatory
              
              DESCRIPTION
                      "Host name assigned by DHCP of IP host"
              ::= { onuIPHostStateEntry 17 }

-- ONU UNI LLDP远端信息表 

    -- onuUniLldpRemTable
            onuUniLldpRemTable OBJECT-TYPE
                SYNTAX  SEQUENCE OF OnuUniLldpRemEntry
                ACCESS  not-accessible
                STATUS  mandatory
                DESCRIPTION
                    "A list of ONU lldp remote information table entries."
                ::= { nmsGponUNIPortObj 11 }

            onuUniLldpRemEntry OBJECT-TYPE
                SYNTAX  OnuUniLldpRemEntry
                ACCESS  not-accessible
                STATUS  mandatory
                DESCRIPTION
                    "A list of onuUniLldpRemEntry."
                INDEX { onuUniLldpRemLocalDeviceIndex, onuUniLldpRemLocalPortIndex, onuUniLldpRemEntryIndex }
                ::= { onuUniLldpRemTable 1 }

            OnuUniLldpRemEntry ::=
                SEQUENCE {
                    onuUniLldpRemLocalDeviceIndex
                        INTEGER,
                    onuUniLldpRemLocalPortIndex
                        INTEGER,
                    onuUniLldpRemEntryIndex
                        INTEGER,
                    onuUniLldpRemChassisIdSubtype
                        INTEGER,
                    onuUniLldpRemChassisId
                        OCTET STRING,
                    onuUniLldpRemPortIdSubtype
                        INTEGER,
                    onuUniLldpRemPortId
                        OCTET STRING,
                    onuUniLldpRemPortDesc
                        OCTET STRING,
                    onuUniLldpRemSysName
                        OCTET STRING,
                    onuUniLldpRemSysDesc
                        OCTET STRING,
                    onuUniLldpRemSysCapSupported
                        BITS,
                    onuUniLldpRemSysCapEnabled
                        BITS,
                    onuUniLldpRemLastUpdate
                        TimeTicks
                }

            onuUniLldpRemLocalDeviceIndex OBJECT-TYPE
                SYNTAX  INTEGER
                ACCESS  read-only
                STATUS  mandatory
                DESCRIPTION
                    "ONU interface id, unique in system.
                    The same value as ifTable index.
                    "
                ::= { onuUniLldpRemEntry 1 }

            onuUniLldpRemLocalPortIndex OBJECT-TYPE
                SYNTAX  INTEGER
                ACCESS  read-only
                STATUS  mandatory
                DESCRIPTION
                    "ONU uni port sequence number,unique in one ONU."
                ::= { onuUniLldpRemEntry 2 }

            onuUniLldpRemEntryIndex OBJECT-TYPE
                SYNTAX  INTEGER
                ACCESS  read-only
                STATUS  mandatory
                DESCRIPTION
                    "ONU uni port lldp remote entry index."
                ::= { onuUniLldpRemEntry 3 }

            onuUniLldpRemChassisIdSubtype OBJECT-TYPE
                SYNTAX  INTEGER{
                        chassisComponent(1),
                        interfaceAlias(2),
                        portComponent(3),
                        macAddress(4),
                        networkAddress(5),
                        interfaceName(6),
                        local(7)
                        }
                ACCESS  read-only
                STATUS  mandatory
                DESCRIPTION
                    "ONU uni port lldp remote chassis id subtype."
                ::= { onuUniLldpRemEntry 4 }

            onuUniLldpRemChassisId OBJECT-TYPE
                SYNTAX  OCTET STRING (SIZE (0..32))
                ACCESS  read-only
                STATUS  mandatory
                DESCRIPTION
                    "ONU uni port lldp remote chassis id."
                ::= { onuUniLldpRemEntry 5 }

            onuUniLldpRemPortIdSubtype OBJECT-TYPE
                SYNTAX  INTEGER{
                        interfaceAlias(1),
                        portComponent(2),
                        macAddress(3),
                        networkAddress(4),
                        interfaceName(5),
                        agentCircuitId(6),
                        local(7)
                        }
                ACCESS  read-only
                STATUS  mandatory
                DESCRIPTION
                    "ONU uni port lldp remote port id subtype."
                ::= { onuUniLldpRemEntry 6 }

            onuUniLldpRemPortId OBJECT-TYPE
                SYNTAX  OCTET STRING (SIZE (0..32))
                ACCESS  read-only
                STATUS  mandatory
                DESCRIPTION
                    "ONU uni port lldp remote port id."
                ::= { onuUniLldpRemEntry 7 }

            onuUniLldpRemPortDesc OBJECT-TYPE
                SYNTAX  OCTET STRING (SIZE (0..59))
                ACCESS  read-only
                STATUS  mandatory
                DESCRIPTION
                    "ONU uni port lldp remote port description."
                ::= { onuUniLldpRemEntry 8 }

            onuUniLldpRemSysName OBJECT-TYPE
                SYNTAX  OCTET STRING (SIZE (0..126))
                ACCESS  read-only
                STATUS  mandatory
                DESCRIPTION
                    "ONU uni port lldp remote system name."
                ::= { onuUniLldpRemEntry 9 }

            onuUniLldpRemSysDesc OBJECT-TYPE
                SYNTAX  OCTET STRING (SIZE (0..256))
                ACCESS  read-only
                STATUS  mandatory
                DESCRIPTION
                    "ONU uni port lldp remote system name description."
                ::= { onuUniLldpRemEntry 10 }

            onuUniLldpRemSysCapSupported OBJECT-TYPE
                SYNTAX  BITS{
                    other(0),
                    repeater(1),
                    bridge(2),
                    wlanAccessPoint(3),
                    router(4),
                    telephone(5),
                    docsisCableDevice(6),
                    stationOnly(7)
                    }
                ACCESS  read-only
                STATUS  mandatory
                DESCRIPTION
                    "ONU uni port lldp remote system capability supported."
                ::= { onuUniLldpRemEntry 11 }

            onuUniLldpRemSysCapEnabled OBJECT-TYPE
                SYNTAX  BITS{
                    other(0),
                    repeater(1),
                    bridge(2),
                    wlanAccessPoint(3),
                    router(4),
                    telephone(5),
                    docsisCableDevice(6),
                    stationOnly(7)
                    }
                ACCESS  read-only
                STATUS  mandatory
                DESCRIPTION
                    "ONU uni port lldp remote system capability enabled."
                ::= { onuUniLldpRemEntry 12 }

            onuUniLldpRemLastUpdate OBJECT-TYPE
                SYNTAX  TimeTicks
                ACCESS  read-only
                STATUS  mandatory
                DESCRIPTION
                    "ONU uni port lldp remote entry last update time."
                ::= { onuUniLldpRemEntry 13 }


-- ONU UNI 802.1x认证状态表 

    -- onuUniDot1xAuthStateTable
            onuUniDot1xAuthStateTable OBJECT-TYPE
                SYNTAX  SEQUENCE OF OnuUniDot1xAuthStateEntry
                ACCESS  not-accessible
                STATUS  mandatory
                DESCRIPTION
                    "A list of ONU 802.1x authentication state table entries."
                ::= { nmsGponUNIPortObj 12 }

            onuUniDot1xAuthStateEntry OBJECT-TYPE
                SYNTAX  OnuUniDot1xAuthStateEntry
                ACCESS  not-accessible
                STATUS  mandatory
                DESCRIPTION
                    "A list of onuUniDot1xAuthStateEntry."
                INDEX { onuUniDot1xAuthStateDeviceIndex, onuUniDot1xAuthStatePortIndex, onuUniDot1xAuthStateEntryIndex }
                ::= { onuUniDot1xAuthStateTable 1 }

            OnuUniDot1xAuthStateEntry ::=
                SEQUENCE {
                    onuUniDot1xAuthStateDeviceIndex
                        INTEGER,
                    onuUniDot1xAuthStatePortIndex
                        INTEGER,
                    onuUniDot1xAuthStateEntryIndex
                        INTEGER,
                    onuUniDot1xAuthStateSupplicantMac
                        MacAddress,
                    onuUniDot1xAuthStateAuthorized
                        INTEGER,
                    onuUniDot1xAuthStatePAE
                        INTEGER,
                    onuUniDot1xAuthStateBEA
                        INTEGER
                }

            onuUniDot1xAuthStateDeviceIndex OBJECT-TYPE
                SYNTAX  INTEGER
                ACCESS  read-only
                STATUS  mandatory
                DESCRIPTION
                    "ONU interface id, unique in system.
                    The same value as ifTable index.
                    "
                ::= { onuUniDot1xAuthStateEntry 1 }

            onuUniDot1xAuthStatePortIndex OBJECT-TYPE
                SYNTAX  INTEGER
                ACCESS  read-only
                STATUS  mandatory
                DESCRIPTION
                    "ONU uni port sequence number,unique in one ONU."
                ::= { onuUniDot1xAuthStateEntry 2 }

            onuUniDot1xAuthStateEntryIndex OBJECT-TYPE
                SYNTAX  INTEGER
                ACCESS  read-only
                STATUS  mandatory
                DESCRIPTION
                    "ONU uni port 802.1x authentication state entry index."
                ::= { onuUniDot1xAuthStateEntry 3 }

            onuUniDot1xAuthStateSupplicantMac OBJECT-TYPE
                SYNTAX  MacAddress
                ACCESS  read-only
                STATUS  mandatory
                DESCRIPTION
                    "ONU uni port 802.1x authentication supplicant mac address.
                     Mac address with all zero means Unknown.
                    "
                ::= { onuUniDot1xAuthStateEntry 4 }

            onuUniDot1xAuthStateAuthorized OBJECT-TYPE
                SYNTAX  INTEGER{
                        authorized(1),
                        unauthorized(2)
                        }
                ACCESS  read-only
                STATUS  mandatory
                DESCRIPTION
                    "ONU uni port 802.1x authentication authorized state."
                ::= { onuUniDot1xAuthStateEntry 5 }

            onuUniDot1xAuthStatePAE OBJECT-TYPE
                SYNTAX  INTEGER{
                        initialize(0),
                        disconnected(1),
                        connecting(2),
                        authenticating(3),
                        authenticated(4),
                        aborting(5),
                        held(6),
                        force-auth(7),
                        force-unauth(8),
                        restart(9)
                        }
                ACCESS  read-only
                STATUS  mandatory
                DESCRIPTION
                    "ONU uni port 802.1x authenticator state."
                ::= { onuUniDot1xAuthStateEntry 6 }

            onuUniDot1xAuthStateBEA OBJECT-TYPE
                SYNTAX  INTEGER{
                        request(0),
                        response(1),
                        success(2),
                        fail(3),
                        timeout(4),
                        idle(5),
                        initialize(6),
                        ignore(7)
                        }
                ACCESS  read-only
                STATUS  mandatory
                DESCRIPTION
                    "ONU uni port 802.1x back-end authentication state."
                ::= { onuUniDot1xAuthStateEntry 7 }

-- 通用端口信息表

             onuGeneralUniInfoTable OBJECT-TYPE
                 SYNTAX  SEQUENCE OF OnuGeneralUniInfoEntry
                 ACCESS  not-accessible
                 STATUS  mandatory
                 DESCRIPTION
                          "Onu general UNI port information table."
                 ::= { nmsGponUNIPortObj 13 }

             onuGeneralUniInfoEntry OBJECT-TYPE
                 SYNTAX OnuGeneralUniInfoEntry
                 ACCESS  not-accessible
                 STATUS  mandatory
                 DESCRIPTION
                          "Onu general UNI port information table entry."
                 INDEX { onuGeneralUniInfoDeviceIndex, onuGeneralUniInfoPortIndex }
             ::= { onuGeneralUniInfoTable 1 }

             OnuGeneralUniInfoEntry ::=
                 SEQUENCE {
                     onuGeneralUniInfoDeviceIndex
                         INTEGER,
                     onuGeneralUniInfoPortIndex
                         INTEGER,
                     onuGeneralUniInfoPortType
                         INTEGER,
                     onuGeneralUniInfoIndexOfType
                         INTEGER,
                     onuGeneralUniInfoMgmtCapability
                         INTEGER
                }
                     
                     
              onuGeneralUniInfoDeviceIndex OBJECT-TYPE
                  SYNTAX  INTEGER
                  ACCESS  read-only
                  STATUS  mandatory

                  DESCRIPTION
                          "ONU interface id, unique in system.
                           The same value as ifTable index.
                          "
                  ::= { onuGeneralUniInfoEntry 1 }


              onuGeneralUniInfoPortIndex OBJECT-TYPE
                  SYNTAX  INTEGER
                  ACCESS  read-only
                  STATUS  mandatory

                  DESCRIPTION
                          "Port Index"
                  ::= { onuGeneralUniInfoEntry 2 }

              onuGeneralUniInfoPortType OBJECT-TYPE
                  SYNTAX  INTEGER{
                                   ethernet-uni(1),
                                   pots-uni(2),
                                   veip(3),
                                   video-uni(4),
                                   video-ani(5),
                                   other(256)
                                 }
                  ACCESS  read-create
                  STATUS  mandatory

                  DESCRIPTION
                          "Port type"
                  ::= { onuGeneralUniInfoEntry 3 }

              onuGeneralUniInfoIndexOfType OBJECT-TYPE
                  SYNTAX  INTEGER
                  ACCESS  read-create
                  STATUS  mandatory
                  
                  DESCRIPTION
                          "Index of port within the same port type."
                  ::= { onuGeneralUniInfoEntry 4 }

              onuGeneralUniInfoMgmtCapability OBJECT-TYPE
                  SYNTAX  INTEGER{
                                   omci-only(1),
                                   non-omci-only(2),
                                   both(3)
                                 }
                  ACCESS  read-create
                  STATUS  mandatory
                  
                  DESCRIPTION
                          "Management capability of the port. "
                  ::= { onuGeneralUniInfoEntry 5 }


-- 通用端口配置表

             onuGeneralUniConfigTable OBJECT-TYPE
                 SYNTAX  SEQUENCE OF OnuGeneralUniConfigEntry
                 ACCESS  not-accessible
                 STATUS  mandatory
                 DESCRIPTION
                          "Onu general UNI port config table."
                 ::= { nmsGponUNIPortObj 14 }

             onuGeneralUniConfigEntry OBJECT-TYPE
                 SYNTAX OnuGeneralUniConfigEntry
                 ACCESS  not-accessible
                 STATUS  mandatory
                 DESCRIPTION
                          "Onu general UNI port config table entry."
                 INDEX { onuGeneralUniConfigDeviceIndex, onuGeneralUniConfigPortIndex }
             ::= { onuGeneralUniConfigTable 1 }

             OnuGeneralUniConfigEntry ::=
                 SEQUENCE {
                     onuGeneralUniConfigDeviceIndex
                         INTEGER,
                     onuGeneralUniConfigPortIndex
                         INTEGER,
                     onuGeneralUniConfigAdminState
                         INTEGER,
                     onuGeneralUniConfigRowStatus
                         RowStatus
                }
                     
                     
              onuGeneralUniConfigDeviceIndex OBJECT-TYPE
                  SYNTAX  INTEGER
                  ACCESS  read-only
                  STATUS  mandatory

                  DESCRIPTION
                          "ONU interface id, unique in system.
                           The same value as ifTable index.
                          "
                  ::= { onuGeneralUniConfigEntry 1 }


              onuGeneralUniConfigPortIndex OBJECT-TYPE
                  SYNTAX  INTEGER
                  ACCESS  read-only
                  STATUS  mandatory

                  DESCRIPTION
                          "Port Index"
                  ::= { onuGeneralUniConfigEntry 2 }

              onuGeneralUniConfigAdminState OBJECT-TYPE
                  SYNTAX  INTEGER{
                                   no-shutdown(1),
                                   shutdown(2)
                                 }
                  ACCESS  read-create
                  STATUS  mandatory

                  DESCRIPTION
                          "1-No shutdown  2-Shutdown "
                  ::= { onuGeneralUniConfigEntry 3 }

              onuGeneralUniConfigRowStatus OBJECT-TYPE
                  SYNTAX  RowStatus
                  ACCESS  read-create
                  STATUS  mandatory

                  DESCRIPTION
                          ""
                  ::= { onuGeneralUniConfigEntry 4 }

-- nmsGponVirPortObj 虚端口任务 OID:1.3.6.1.4.1.3320.10.5

nmsGponVirPortObj   OBJECT IDENTIFIER ::= { nmsGponMIB 5 }  

-- ONU虚端口配置表

             onuVirPortConfigTable OBJECT-TYPE
                 SYNTAX  SEQUENCE OF OnuVirPortConfigEntry
                 ACCESS  not-accessible
                 STATUS  mandatory
                 DESCRIPTION
                          "Onu VIR port config table."
                 ::= { nmsGponVirPortObj 1 }

             onuVirPortConfigEntry OBJECT-TYPE
                 SYNTAX OnuVirPortConfigEntry
                 ACCESS  not-accessible
                 STATUS  mandatory
                 DESCRIPTION
                          "Onu VIR port config table entry."
                 INDEX { onuVirPortConfigDeviceIndex, onuVirPortConfigPortIndex }
             ::= { onuVirPortConfigTable 1 }

             OnuVirPortConfigEntry ::=
                 SEQUENCE {
                     onuVirPortConfigDeviceIndex
                         INTEGER,
                     onuVirPortConfigPortIndex
                         INTEGER,
                     onuVirPortConfigTCONTID
                         INTEGER,
                     onuVirPortConfigOltGEMPortID
                         INTEGER,
                     onuVirPortConfigOltAllocID
                         INTEGER,
                     onuVirPortConfigVirPortAdminState
                         INTEGER,
                     onuVirPortConfigEncryptionMode
                         INTEGER,
                     onuVirPortConfigDownstreamRateLimit
                         INTEGER,
                     onuVirPortConfigOltVLANTranslationProfileID
                         INTEGER,
                     onuVirPortConfigONUMacFilterProfileID
                         INTEGER,
                     onuVirPortConfigONUMacFilterPreassignProfileID
                         INTEGER,
                     onuVirPortConfigRowStatus
                         RowStatus,
                     onuVirPortConfigDownstreamRateLimitPir
                         INTEGER
            }
                 
                 
          onuVirPortConfigDeviceIndex OBJECT-TYPE
              SYNTAX  INTEGER
              ACCESS  read-only
              STATUS  mandatory

              DESCRIPTION
                      ""
              ::= { onuVirPortConfigEntry 1 }

          onuVirPortConfigPortIndex OBJECT-TYPE
              SYNTAX  INTEGER
              ACCESS  read-only
              STATUS  mandatory

              DESCRIPTION
                      ""
              ::= { onuVirPortConfigEntry 2 }

          onuVirPortConfigTCONTID OBJECT-TYPE
              SYNTAX  INTEGER
              ACCESS  read-write
              STATUS  mandatory

              DESCRIPTION
                      "Static T-CONT index from ONU’s perspective. Default value is 1. "
              ::= { onuVirPortConfigEntry 3 }
          onuVirPortConfigOltGEMPortID OBJECT-TYPE
              SYNTAX  INTEGER
              ACCESS  read-write
              STATUS  mandatory

              DESCRIPTION
                      "EM port no which is assigned dynamically by OLT. "
              ::= { onuVirPortConfigEntry 4 }
          onuVirPortConfigOltAllocID OBJECT-TYPE
              SYNTAX  INTEGER
              ACCESS  read-write
              STATUS  mandatory

              DESCRIPTION
                      "lloc-ID which is assigned dynamically by OLT, a dynamic Alloc-ID is one-to-one mapped 
                      to a static T-CONT index."
              ::= { onuVirPortConfigEntry 5 }
          onuVirPortConfigVirPortAdminState OBJECT-TYPE
              SYNTAX  INTEGER{
                               no-shutdown-unlocks(1),
                               shutdown-locks(2)
                             }

              ACCESS  read-write
              STATUS  mandatory

              DESCRIPTION
                      "This attribute locks and unlocks the functions performed by this managed entity. 1 No
                       shutdown/unlocks, 2 Shutdown/locks. "
              ::= { onuVirPortConfigEntry 6 }
          onuVirPortConfigEncryptionMode OBJECT-TYPE
              SYNTAX  INTEGER{
                               enable(1),
                               disable(2)
                             }

              ACCESS  read-write
              STATUS  mandatory

              DESCRIPTION
                      "The encryption mode for the GEM port. Possible values are: 1 (Enabled), 2 (Disabled). "
              ::= { onuVirPortConfigEntry 7 }
          onuVirPortConfigDownstreamRateLimit OBJECT-TYPE
              SYNTAX  INTEGER
              ACCESS  read-write
              STATUS  mandatory

              DESCRIPTION
                      "Config Virtual port downstream rate limit(unit:64kbps).
                      If onuVirPortConfigDownstreamRateLimitPir equals 0, RFC2697(srTCM) policy is used. onuVirPortConfigDownstreamRateLimit act as the CIR of RFC2697.
                      If onuVirPortConfigDownstreamRateLimitPir is not 0, RFC2698(trTCM) policy is used. onuVirPortConfigDownstreamRateLimitPir act as the PIR, and onuVirPortConfigDownstreamRateLimit act as the CIR of RFC2698. onuVirPortConfigDownstreamRateLimit should be less or equal than onuVirPortConfigDownstreamRateLimitPir."
              ::= { onuVirPortConfigEntry 8 }
          onuVirPortConfigOltVLANTranslationProfileID OBJECT-TYPE
              SYNTAX  INTEGER(1..1024)
              ACCESS  read-write
              STATUS  mandatory

              DESCRIPTION
                      "It stores the profileIndex1 of the associated OLT VLAN translation profile. 1–1024."
              ::= { onuVirPortConfigEntry 9 }
          onuVirPortConfigONUMacFilterProfileID OBJECT-TYPE
              SYNTAX  INTEGER
              ACCESS  read-write
              STATUS  mandatory

              DESCRIPTION
                      ""
              ::= { onuVirPortConfigEntry 10 }
          onuVirPortConfigONUMacFilterPreassignProfileID OBJECT-TYPE
              SYNTAX  INTEGER
              ACCESS  read-write
              STATUS  mandatory

              DESCRIPTION
                      ""
              ::= { onuVirPortConfigEntry 11 }
          onuVirPortConfigRowStatus OBJECT-TYPE
              SYNTAX  RowStatus
              ACCESS  read-create
              STATUS  mandatory

              DESCRIPTION
                      ""
              ::= { onuVirPortConfigEntry 12 }
          onuVirPortConfigDownstreamRateLimitPir OBJECT-TYPE
              SYNTAX  INTEGER
              ACCESS  read-write
              STATUS  mandatory

              DESCRIPTION
                      "Config Virtual port downstream rate limit pir(unit:64kbps). 
                      If onuVirPortConfigDownstreamRateLimitPir equals 0, RFC2697(srTCM) policy is used. onuVirPortConfigDownstreamRateLimit act as the CIR of RFC2697.
                      If onuVirPortConfigDownstreamRateLimitPir is not 0, RFC2698(trTCM) policy is used. onuVirPortConfigDownstreamRateLimitPir act as the PIR, and onuVirPortConfigDownstreamRateLimit act as the CIR of RFC2698. onuVirPortConfigDownstreamRateLimit should be less or equal than onuVirPortConfigDownstreamRateLimitPir."
              ::= { onuVirPortConfigEntry 13 }

-- 虚端口报文统计表

             onuVirPortStatisticTable OBJECT-TYPE
                 SYNTAX  SEQUENCE OF OnuVirPortStatisticEntry
                 ACCESS  not-accessible
                 STATUS  mandatory
                 DESCRIPTION
                          "Onu VIR port statistics table."
                 ::= { nmsGponVirPortObj 2 }

             onuVirPortStatisticEntry OBJECT-TYPE
                 SYNTAX OnuVirPortStatisticEntry
                 ACCESS  not-accessible
                 STATUS  mandatory
                 DESCRIPTION
                          "Onu VIR port statistics table entry."
                 INDEX { onuVirPortStatisticDeviceIndex, onuVirPortStatisticVirPortIndex }
             ::= { onuVirPortStatisticTable 1 }

             OnuVirPortStatisticEntry ::=
                 SEQUENCE {
                     onuVirPortStatisticDeviceIndex
                         INTEGER,
                     onuVirPortStatisticVirPortIndex
                         INTEGER,
                     onuVirPortStatisticTime
                         Counter64,
                     onuVirPortStatisticRxTotalFrames
                         Counter64,
                     onuVirPortStatisticTxTotalFrames
                         Counter64,
                     onuVirPortStatisticRxTotalBytes
                         Counter64,
                     onuVirPortStatisticTxTotalBytes
                         Counter64,
                     onuVirPortStatisticEncryptKeyErrors
                         Counter64
            }
                 
                 
          onuVirPortStatisticDeviceIndex OBJECT-TYPE
              SYNTAX  INTEGER
              ACCESS  read-only
              STATUS  mandatory

              DESCRIPTION
                      ""
              ::= { onuVirPortStatisticEntry 1 }

          onuVirPortStatisticVirPortIndex OBJECT-TYPE
              SYNTAX  INTEGER
              ACCESS  read-only
              STATUS  mandatory

              DESCRIPTION
                      ""
              ::= { onuVirPortStatisticEntry 2 }

          onuVirPortStatisticTime OBJECT-TYPE
              SYNTAX  Counter64
              ACCESS  read-only
              STATUS  mandatory

              DESCRIPTION
                      ""
              ::= { onuVirPortStatisticEntry 3 }

          onuVirPortStatisticRxTotalFrames OBJECT-TYPE
              SYNTAX  Counter64
              ACCESS  read-only
              STATUS  mandatory

              DESCRIPTION
                      ""
              ::= { onuVirPortStatisticEntry 4 }

          onuVirPortStatisticTxTotalFrames OBJECT-TYPE
              SYNTAX  Counter64
              ACCESS  read-only
              STATUS  mandatory

              DESCRIPTION
                      ""
              ::= { onuVirPortStatisticEntry 5 }

          onuVirPortStatisticRxTotalBytes OBJECT-TYPE
              SYNTAX  Counter64
              ACCESS  read-only
              STATUS  mandatory

              DESCRIPTION
                      ""
              ::= { onuVirPortStatisticEntry 6 }

          onuVirPortStatisticTxTotalBytes OBJECT-TYPE
              SYNTAX  Counter64
              ACCESS  read-only
              STATUS  mandatory

              DESCRIPTION
                      ""
              ::= { onuVirPortStatisticEntry 7 }

          onuVirPortStatisticEncryptKeyErrors OBJECT-TYPE
              SYNTAX  Counter64
              ACCESS  read-only
              STATUS  mandatory

              DESCRIPTION
                      ""
              ::= { onuVirPortStatisticEntry 8 }







-- 虚端口15Min报文统计表

             onuVirPort15MinStatisticTable OBJECT-TYPE
                 SYNTAX  SEQUENCE OF OnuVirPort15MinStatisticEntry
                 ACCESS  not-accessible
                 STATUS  mandatory
                 DESCRIPTION
                          "Onu VIR port 15 minutes statistics table."
                 ::= { nmsGponVirPortObj 3 }

             onuVirPort15MinStatisticEntry OBJECT-TYPE
                 SYNTAX OnuVirPort15MinStatisticEntry
                 ACCESS  not-accessible
                 STATUS  mandatory
                 DESCRIPTION
                          "Onu VIR port minutes statistics table entry."
                 INDEX { onuVirPort15MinStatisticDeviceIndex, onuVirPort15MinStatisticVirPortIndex, onuVirPort15MinStatisticIntervalID }
             ::= { onuVirPort15MinStatisticTable 1 }

             OnuVirPort15MinStatisticEntry ::=
                 SEQUENCE {
                     onuVirPort15MinStatisticDeviceIndex
                         INTEGER,
                     onuVirPort15MinStatisticVirPortIndex
                         INTEGER,
                     onuVirPort15MinStatisticIntervalID
                         INTEGER,
                     onuVirPort15MinStatisticRxTotalFrames
                         Counter64,
                     onuVirPort15MinStatisticTxTotalFrames
                         Counter64,
                     onuVirPort15MinStatisticRxTotalBytes
                         Counter64,
                     onuVirPort15MinStatisticTxTotalBytes
                         Counter64,
                     onuVirPort15MinStatisticEncryptKeyErrors
                         Counter64
            }
                 
                 
          onuVirPort15MinStatisticDeviceIndex OBJECT-TYPE
              SYNTAX  INTEGER
              ACCESS  read-only
              STATUS  mandatory

              DESCRIPTION
                      ""
              ::= { onuVirPort15MinStatisticEntry 1 }

          onuVirPort15MinStatisticVirPortIndex OBJECT-TYPE
              SYNTAX  INTEGER
              ACCESS  read-only
              STATUS  mandatory

              DESCRIPTION
                      ""
              ::= { onuVirPort15MinStatisticEntry 2 }

          onuVirPort15MinStatisticIntervalID OBJECT-TYPE
              SYNTAX  INTEGER
              ACCESS  read-only
              STATUS  mandatory

              DESCRIPTION
                      ""
              ::= { onuVirPort15MinStatisticEntry 3 }

          onuVirPort15MinStatisticRxTotalFrames OBJECT-TYPE
              SYNTAX  Counter64
              ACCESS  read-only
              STATUS  mandatory

              DESCRIPTION
                      ""
              ::= { onuVirPort15MinStatisticEntry 4 }

          onuVirPort15MinStatisticTxTotalFrames OBJECT-TYPE
              SYNTAX  Counter64
              ACCESS  read-only
              STATUS  mandatory

              DESCRIPTION
                      ""
              ::= { onuVirPort15MinStatisticEntry 5 }

          onuVirPort15MinStatisticRxTotalBytes OBJECT-TYPE
              SYNTAX  Counter64
              ACCESS  read-only
              STATUS  mandatory

              DESCRIPTION
                      ""
              ::= { onuVirPort15MinStatisticEntry 6 }

          onuVirPort15MinStatisticTxTotalBytes OBJECT-TYPE
              SYNTAX  Counter64
              ACCESS  read-only
              STATUS  mandatory

              DESCRIPTION
                      ""
              ::= { onuVirPort15MinStatisticEntry 7 }

          onuVirPort15MinStatisticEncryptKeyErrors OBJECT-TYPE
              SYNTAX  Counter64
              ACCESS  read-only
              STATUS  mandatory

              DESCRIPTION
                      ""
              ::= { onuVirPort15MinStatisticEntry 8 }
 
 
 
 
 
 
 --虚端口VLAN翻译表

             onuVirPortDot1qTranslatTable OBJECT-TYPE
                 SYNTAX  SEQUENCE OF OnuVirPortDot1qTranslatEntry
                 ACCESS  not-accessible
                 STATUS  mandatory
                 DESCRIPTION
                          "Config table for VLAN translation based on onu VIR port."
                 ::= { nmsGponVirPortObj 4 }

             onuVirPortDot1qTranslatEntry OBJECT-TYPE
                 SYNTAX OnuVirPortDot1qTranslatEntry
                 ACCESS  not-accessible
                 STATUS  mandatory
                 DESCRIPTION
                          "Config entry for VLAN translation based on onu VIR port."
                 INDEX { onuVirPortDot1qTranslatDeviceIndex, onuVirPortDot1qTranslatVirPortIndex, onuVirPortDot1qTranslatEntryIndex }
             ::= { onuVirPortDot1qTranslatTable 1 }

             OnuVirPortDot1qTranslatEntry ::=
                 SEQUENCE {
                     onuVirPortDot1qTranslatDeviceIndex
                         INTEGER,
                     onuVirPortDot1qTranslatVirPortIndex
                         INTEGER,
                     onuVirPortDot1qTranslatEntryIndex
                         INTEGER,
                     onuVirPortDot1qTranslatMode
                         INTEGER,
                     onuVirPortDot1qTranslatNto1
                         INTEGER,
                     onuVirPortDot1qTranslatSorVlanStart
                         INTEGER,
                     onuVirPortDot1qTranslatSorVlanEnd
                         INTEGER,
                     onuVirPortDot1qTranslatSorVlanMap
                         OCTET STRING,
                     onuVirPortDot1qTranslatDstVlan
                         INTEGER,
                     onuVirPortDot1qTranslatMixVlan
                         INTEGER,
                     onuVirPortDot1qTranslatPriority
                         INTEGER,
                     onuVirPortDot1qTranslatRowStatus
                         RowStatus
            }
                 
                 
          onuVirPortDot1qTranslatDeviceIndex OBJECT-TYPE
              SYNTAX  INTEGER
              ACCESS  read-only
              STATUS  mandatory

              DESCRIPTION
                      "ONU diID"
              ::= { onuVirPortDot1qTranslatEntry 1 }

          onuVirPortDot1qTranslatVirPortIndex OBJECT-TYPE
              SYNTAX  INTEGER
              ACCESS  read-only
              STATUS  mandatory

              DESCRIPTION
                      "ONU virtual port ID"
              ::= { onuVirPortDot1qTranslatEntry 2 }

          onuVirPortDot1qTranslatEntryIndex OBJECT-TYPE
              SYNTAX  INTEGER
              ACCESS  read-only
              STATUS  mandatory

              DESCRIPTION
                      "ONU virtual VLAN translation config entry index"
              ::= { onuVirPortDot1qTranslatEntry 3 }

          onuVirPortDot1qTranslatMode OBJECT-TYPE
              SYNTAX  INTEGER{
                               flat(1),
                               qinq(2),
                               mix(3),
                               range-flat(4),
                               range-qinq(5)
                             }
              ACCESS  read-write
              STATUS  mandatory

              DESCRIPTION
                      "Vlan translation mode:
                            1--flat;
                            2--QinQ;
                            3--mix;
                            4--range flat;
                            5--range QinQ."
              ::= { onuVirPortDot1qTranslatEntry 4 }

          onuVirPortDot1qTranslatNto1 OBJECT-TYPE
              SYNTAX  INTEGER{
                                oto1(1),
                                nto1(2)
                             }
              ACCESS  read-write
              STATUS  mandatory

              DESCRIPTION
                      "1--1to1; 2--nto1."
              ::= { onuVirPortDot1qTranslatEntry 5 }

          onuVirPortDot1qTranslatSorVlanStart OBJECT-TYPE
              SYNTAX  INTEGER
              ACCESS  read-write
              STATUS  mandatory

              DESCRIPTION
                      "Start VLAN ID(1-4094)."
              ::= { onuVirPortDot1qTranslatEntry 6 }

          onuVirPortDot1qTranslatSorVlanEnd OBJECT-TYPE
              SYNTAX  INTEGER
              ACCESS  read-write
              STATUS  mandatory

              DESCRIPTION
                      "End VLAN ID(1-4094)."
              ::= { onuVirPortDot1qTranslatEntry 7 }

          onuVirPortDot1qTranslatSorVlanMap OBJECT-TYPE
              SYNTAX  OCTET STRING
              ACCESS  read-write
              STATUS  mandatory

              DESCRIPTION
                      "Source VLAN IDs such as (1,3,5,7) Or (1,3-5,7) Or (1-7)."
              ::= { onuVirPortDot1qTranslatEntry 8 } 
 
          onuVirPortDot1qTranslatDstVlan OBJECT-TYPE
              SYNTAX  INTEGER
              ACCESS  read-write
              STATUS  mandatory

              DESCRIPTION
                      "Destination VLAN ID(1-4094)."
              ::= { onuVirPortDot1qTranslatEntry 9 }
              
          onuVirPortDot1qTranslatMixVlan OBJECT-TYPE
              SYNTAX  INTEGER
              ACCESS  read-write
              STATUS  mandatory

              DESCRIPTION
                      "Mix out VLAN ID(1-4094)."
              ::= { onuVirPortDot1qTranslatEntry 10 } 

          onuVirPortDot1qTranslatPriority OBJECT-TYPE
              SYNTAX  INTEGER
              ACCESS  read-write
              STATUS  mandatory

              DESCRIPTION
                      "New 802.1Q priority value(0-7)."
              ::= { onuVirPortDot1qTranslatEntry 11 } 

          onuVirPortDot1qTranslatRowStatus OBJECT-TYPE
              SYNTAX  RowStatus
              ACCESS  read-write
              STATUS  mandatory

              DESCRIPTION
                      ""
              ::= { onuVirPortDot1qTranslatEntry 12 }  
 
 

        
        
        
        
--GPON脚本任务        

nmsGponProfile   OBJECT IDENTIFIER ::= { nmsGponMIB 6 }  

onuVLANProfile   OBJECT IDENTIFIER ::= { nmsGponProfile 1 }  


             onuVLANProfileTable OBJECT-TYPE
                 SYNTAX  SEQUENCE OF OnuVLANProfileEntry
                 ACCESS  not-accessible
                 STATUS  mandatory
                 DESCRIPTION
                          "Onu VLAN Profile table."
                 ::= { onuVLANProfile 1 }

             onuVLANProfileEntry OBJECT-TYPE
                 SYNTAX OnuVLANProfileEntry
                 ACCESS  not-accessible
                 STATUS  mandatory
                 DESCRIPTION
                          "Onu VLAN Profile."
                 INDEX { onuVLANProfileIndex }
             ::= { onuVLANProfileTable 1 }

             OnuVLANProfileEntry ::=
                 SEQUENCE {
                     onuVLANProfileIndex
                         INTEGER,
                     onuVLANProfileName
                         OCTET STRING,
                     onuVLANProfileVlanMode
                         INTEGER,
                     onuVLANProfilePVID
                         INTEGER,   
                     onuVLANProfileTrunkVlans 
                         OCTET STRING,
                     onuVLANProfileEtherTypeIPOEVlan
                         INTEGER,   
                     onuVLANProfileEtherTypePPPOEVlan
                         INTEGER,   
                     onuVLANProfileEtherTypeARPVlan
                         INTEGER,                            
                     onuVLANProfileRowStatus
                         RowStatus,
                     onuVLANProfileEtherTypeIPv6Vlan
                         INTEGER,
                     onuVLANProfileEtherTypeIPOECos
                         INTEGER,   
                     onuVLANProfileEtherTypePPPOECos
                         INTEGER,   
                     onuVLANProfileEtherTypeARPCos
                         INTEGER,                            
                     onuVLANProfileEtherTypeIPv6Cos
                         INTEGER,                                  
                     onuVLANProfilePVIDStart                                 
                         INTEGER, 
                     onuVLANProfilePVIDStep                                 
                         INTEGER,
                     onuVLANProfilePVIDCos                                 
                         INTEGER,
                     onuVLANProfileEtherTypeIPOEVlanSTART
                         INTEGER,   
                     onuVLANProfileEtherTypePPPOEVlanSTART
                         INTEGER,   
                     onuVLANProfileEtherTypeARPVlanSTART
                         INTEGER,                            
                     onuVLANProfileEtherTypeIPv6VlanSTART
                         INTEGER,
                     onuVLANProfileEtherTypeIPOEVlanSTEP
                         INTEGER,   
                     onuVLANProfileEtherTypePPPOEVlanSTEP
                         INTEGER,   
                     onuVLANProfileEtherTypeARPVlanSTEP
                         INTEGER,                            
                     onuVLANProfileEtherTypeIPv6VlanSTEP
                         INTEGER,   
                 }
                 
                 
          onuVLANProfileIndex OBJECT-TYPE
              SYNTAX  INTEGER
              ACCESS  read-only
              STATUS  mandatory

              DESCRIPTION
                      "Index of the table, ONU VLAN INDEX."
              ::= { onuVLANProfileEntry 1 }
                 
          onuVLANProfileName OBJECT-TYPE
              SYNTAX  OCTET STRING
              ACCESS  read-write
              STATUS  mandatory

              DESCRIPTION
                      "Name of VLAN profile."
              ::= { onuVLANProfileEntry 2 }
                 
          onuVLANProfileVlanMode OBJECT-TYPE
              SYNTAX  INTEGER{
                               transparent(1),
                               tag(2),
                               translation(3),
                               vlan-stacking(4),
                               aggregation(5),
                               trunk(6)
                              }
              ACCESS  read-write
              STATUS  mandatory

              DESCRIPTION
                      "  1 Transparent,2 Tag, 3 Translation,4 Vlan-stacking, 5 Aggregation,6 Trunk. Defualt value is 1."
              ::= { onuVLANProfileEntry 3 }
                 
          onuVLANProfilePVID OBJECT-TYPE
              SYNTAX  INTEGER(1..4094)
              ACCESS  read-write
              STATUS  mandatory

              DESCRIPTION
                      "The pvid of the port(1-4094). Default value is 1."
              ::= { onuVLANProfileEntry 4 }
                 
          onuVLANProfileTrunkVlans OBJECT-TYPE
              SYNTAX  OCTET STRING
              ACCESS  read-write
              STATUS  mandatory

              DESCRIPTION
                      "ONU UNI port allowed VLAN in trunk mode. Config allowed VLAN IDs such as (1,3,5,7) Or (1,3-5,7) 
                      Or (1-7). Default value is 0."
              ::= { onuVLANProfileEntry 5 }
                 
          onuVLANProfileEtherTypeIPOEVlan OBJECT-TYPE
              SYNTAX  INTEGER(1..4095)
              ACCESS  read-write
              STATUS  mandatory

              DESCRIPTION
                      "Config IPOE ethernet type VlanId.1-4094 vlanID, 4095 drop."
              ::= { onuVLANProfileEntry 6 }
                 
          onuVLANProfileEtherTypePPPOEVlan OBJECT-TYPE
              SYNTAX  INTEGER(1..4095)
              ACCESS  read-write
              STATUS  mandatory

              DESCRIPTION
                      "Config PPPOE ethernet type VlanId.1-4094 vlanID, 4095 drop."
              ::= { onuVLANProfileEntry 7 }
                 
          onuVLANProfileEtherTypeARPVlan OBJECT-TYPE
              SYNTAX  INTEGER(1..4095)
              ACCESS  read-write
              STATUS  mandatory

              DESCRIPTION
                      "Config ARP ethernet type VlanId.1-4094 vlanID, 4095 drop."
              ::= { onuVLANProfileEntry 8 }
          
          onuVLANProfileRowStatus OBJECT-TYPE
              SYNTAX  RowStatus
              ACCESS  read-create
              STATUS  mandatory

              DESCRIPTION
                      ""
              ::= { onuVLANProfileEntry 9 }   
              
          onuVLANProfileEtherTypeIPv6Vlan OBJECT-TYPE
              SYNTAX  INTEGER(1..4095)
              ACCESS  read-write
              STATUS  mandatory

              DESCRIPTION
                      "Config IPv6 ethernet type VlanId.1-4094 vlanID, 4095 drop."
              ::= { onuVLANProfileEntry 10 }
              
          onuVLANProfileEtherTypeIPOECos OBJECT-TYPE
              SYNTAX  INTEGER{  
                              cos0(0),
                              cos1(1),
                              cos2(2),
                              cos3(3),
                              cos4(4),
                              cos5(5),
                              cos6(6),
                              cos7(7),
                              by-inner-tag(8),
                              by-outer-tag(9),
                              by-dscp(10),
                              not-assigned(255)
                             }
              ACCESS  read-write
              STATUS  mandatory

              DESCRIPTION
                      "Config IPOE ethernet type COS.0-7 cos 0-7,8 cos by-inner-tag,9 cos by-outer-tag,
                      10 cos by-dscp, 255 cos not-assigned."
              ::= { onuVLANProfileEntry 11 }
                 
          onuVLANProfileEtherTypePPPOECos OBJECT-TYPE
              SYNTAX  INTEGER{  
                              cos0(0),
                              cos1(1),
                              cos2(2),
                              cos3(3),
                              cos4(4),
                              cos5(5),
                              cos6(6),
                              cos7(7),
                              by-inner-tag(8),
                              by-outer-tag(9),
                              by-dscp(10),
                              not-assigned(255)
                             }

              ACCESS  read-write
              STATUS  mandatory

              DESCRIPTION
                      "Config PPPOE ethernet type COS. 0-7 cos 0-7, 8 cos by-inner-tag, 9 cos by-outer-tag, 
                      10 cos by-dscp, 255 cos not-assigned."
              ::= { onuVLANProfileEntry 12 }
                 
          onuVLANProfileEtherTypeARPCos OBJECT-TYPE
              SYNTAX  INTEGER{  
                              cos0(0),
                              cos1(1),
                              cos2(2),
                              cos3(3),
                              cos4(4),
                              cos5(5),
                              cos6(6),
                              cos7(7),
                              by-inner-tag(8),
                              by-outer-tag(9),
                              by-dscp(10),
                              not-assigned(255)
                             }
              ACCESS  read-write
              STATUS  mandatory

              DESCRIPTION
                      "Config ARP ethernet type COS. 0-7 cos 0-7, 8 cos by-inner-tag, 9 cos by-outer-tag, 
                      10 cos by-dscp, 255 cos not-assigned."
              ::= { onuVLANProfileEntry 13 }
          
          onuVLANProfileEtherTypeIPv6Cos OBJECT-TYPE
              SYNTAX  INTEGER{  
                              cos0(0),
                              cos1(1),
                              cos2(2),
                              cos3(3),
                              cos4(4),
                              cos5(5),
                              cos6(6),
                              cos7(7),
                              by-inner-tag(8),
                              by-outer-tag(9),
                              by-dscp(10),
                              not-assigned(255)
                             }
              ACCESS  read-write
              STATUS  mandatory

              DESCRIPTION
                      "Config IPv6 ethernet type COS. 0-7 cos 0-7, 8 cos by-inner-tag, 9 cos by-outer-tag, 
                      10 cos by-dscp, 255 cos not-assigned."
              ::= { onuVLANProfileEntry 14 }
                         
           onuVLANProfilePVIDStart OBJECT-TYPE
              SYNTAX  INTEGER(1..4094)
              ACCESS  read-write
              STATUS  mandatory

              DESCRIPTION
                      "Config  profile VlanId start."
              ::= { onuVLANProfileEntry 15 }
          
          onuVLANProfilePVIDStep    OBJECT-TYPE
              SYNTAX  INTEGER(1..4094)
              ACCESS  read-write
              STATUS  mandatory

              DESCRIPTION
                      "Config profile VlanId step length."
              ::= { onuVLANProfileEntry 16 }  
              
          onuVLANProfilePVIDCos    OBJECT-TYPE
              SYNTAX  INTEGER{  
                              cos0(0),
                              cos1(1),
                              cos2(2),
                              cos3(3),
                              cos4(4),
                              cos5(5),
                              cos6(6),
                              cos7(7),
                              cos-by-inner-tag(8),
                              cos-by-outer-tag(9),
                              cos-by-dscp(10)
                             }
              ACCESS  read-write
              STATUS  mandatory

              DESCRIPTION
                      "Config pvid cos.0-7 cos 0-7,8 cos-by-inner-tag,9 cos-by-outer-tag,
                      10 cos-by-dscp."
              ::= { onuVLANProfileEntry 17 }   
              
          onuVLANProfileEtherTypeIPOEVlanSTART OBJECT-TYPE
              SYNTAX  INTEGER(1..4094)
              ACCESS  read-write
              STATUS  mandatory

              DESCRIPTION
                      "Config IPOE ethernet type VlanId start."
              ::= { onuVLANProfileEntry 18 }
                 
          onuVLANProfileEtherTypePPPOEVlanSTART OBJECT-TYPE
              SYNTAX  INTEGER(1..4094)
              ACCESS  read-write
              STATUS  mandatory

              DESCRIPTION
                      "Config PPPOE ethernet type VlanId start."
              ::= { onuVLANProfileEntry 19 }
                 
          onuVLANProfileEtherTypeARPVlanSTART OBJECT-TYPE
              SYNTAX  INTEGER(1..4094)              ACCESS  read-write
              STATUS  mandatory

              DESCRIPTION
                      "Config ARP ethernet type VlanId start."
              ::= { onuVLANProfileEntry 20 }
          
          onuVLANProfileEtherTypeIPv6VlanSTART OBJECT-TYPE
              SYNTAX  INTEGER(1..4094)
              ACCESS  read-write
              STATUS  mandatory

              DESCRIPTION
                      "Config IPv6 ethernet type VlanId start."
              ::= { onuVLANProfileEntry 21 } 
              
          onuVLANProfileEtherTypeIPOEVlanSTEP OBJECT-TYPE
              SYNTAX  INTEGER(1..4094)
              ACCESS  read-write
              STATUS  mandatory

              DESCRIPTION
                      "Config IPOE ethernet type VlanId step length."
              ::= { onuVLANProfileEntry 22 }
                 
          onuVLANProfileEtherTypePPPOEVlanSTEP OBJECT-TYPE
              SYNTAX  INTEGER(1..4094)
              ACCESS  read-write
              STATUS  mandatory

              DESCRIPTION
                      "Config PPPOE ethernet type VlanId step length."
              ::= { onuVLANProfileEntry 23 }
                 
          onuVLANProfileEtherTypeARPVlanSTEP OBJECT-TYPE
              SYNTAX  INTEGER(1..4094)              
              ACCESS  read-write
              STATUS  mandatory

              DESCRIPTION
                      "Config ARP ethernet type VlanId step length."
              ::= { onuVLANProfileEntry 24 }
          
          onuVLANProfileEtherTypeIPv6VlanSTEP OBJECT-TYPE
              SYNTAX  INTEGER(1..4094)
              ACCESS  read-write
              STATUS  mandatory

              DESCRIPTION
                      "Config IPv6 ethernet type VlanId step length."
              ::= { onuVLANProfileEntry 25 }

--ONU VLAN翻译

             onuVLANTranslationTable OBJECT-TYPE
                 SYNTAX  SEQUENCE OF OnuVLANTranslationEntry
                 ACCESS  not-accessible
                 STATUS  mandatory
                 DESCRIPTION
                          "Onu VLAN translation Profile table."
                 ::= { onuVLANProfile 2 }

             onuVLANTranslationEntry OBJECT-TYPE
                 SYNTAX OnuVLANTranslationEntry
                 ACCESS  not-accessible
                 STATUS  mandatory
                 DESCRIPTION
                          "Onu VLAN translation Profile entry."
                 INDEX { onuVLANTranslationIndex1,onuVLANTranslationIndex2 }
             ::= { onuVLANTranslationTable 1 }

             OnuVLANTranslationEntry ::=
                 SEQUENCE {
                     onuVLANTranslationIndex1
                         INTEGER,
                     onuVLANTranslationIndex2
                         INTEGER,
                     onuVLANTranslationName
                         OCTET STRING,
                     onuVLANTranslationSrcVlan
                         INTEGER,   
                     onuVLANTranslationDstVlan 
                         INTEGER,
                     onuVLANTranslationRowStatus
                         RowStatus                      
                 }
                 
          onuVLANTranslationIndex1 OBJECT-TYPE
              SYNTAX  INTEGER
              ACCESS  read-only
              STATUS  mandatory

              DESCRIPTION
                      "Index of the table, ONU VLAN translation INDEX 1."
              ::= { onuVLANTranslationEntry 1 }
                 
          onuVLANTranslationIndex2 OBJECT-TYPE
              SYNTAX  INTEGER
              ACCESS  read-only
              STATUS  mandatory

              DESCRIPTION
                      "Index of the table, ONU VLAN translation INDEX 2."
              ::= { onuVLANTranslationEntry 2 }
                 
          onuVLANTranslationName OBJECT-TYPE
              SYNTAX  OCTET STRING
              ACCESS  read-only
              STATUS  mandatory

              DESCRIPTION
                      "Name of VLAN translation profile."
              ::= { onuVLANTranslationEntry 3 }
                 
          onuVLANTranslationSrcVlan OBJECT-TYPE
              SYNTAX  INTEGER
              ACCESS  read-only
              STATUS  mandatory

              DESCRIPTION
                      "ONU VLAN translation source VLAN id."
              ::= { onuVLANTranslationEntry 4 }

          onuVLANTranslationDstVlan OBJECT-TYPE
              SYNTAX  INTEGER
              ACCESS  read-only
              STATUS  mandatory

              DESCRIPTION
                      "ONU VLAN translation destination VLAN id."
              ::= { onuVLANTranslationEntry 5 }
      
          onuVLANTranslationRowStatus OBJECT-TYPE
              SYNTAX  RowStatus
              ACCESS  read-create
              STATUS  mandatory

              DESCRIPTION
                      "Config SrcVlan and DstVlan in translation/vlan-stacking/aggregation modes."
              ::= { onuVLANTranslationEntry 6 } 


--ONU T-cont管理表

             onuTCONTServiceProfileTable OBJECT-TYPE
                 SYNTAX  SEQUENCE OF OnuTCONTServiceProfileEntry
                 ACCESS  not-accessible
                 STATUS  mandatory
                 DESCRIPTION
                          "Onu VLAN translation Profile table."
                 ::= { nmsGponProfile 2 }

             onuTCONTServiceProfileEntry OBJECT-TYPE
                 SYNTAX OnuTCONTServiceProfileEntry
                 ACCESS  not-accessible
                 STATUS  mandatory
                 DESCRIPTION
                          "Onu VLAN translation Profile entry."
                 INDEX { onuTcontServiceProfileIndex }
             ::= { onuTCONTServiceProfileTable 1 }

             OnuTCONTServiceProfileEntry ::=
                 SEQUENCE {
                     onuTcontServiceProfileIndex
                         INTEGER,
                     onuTcontServiceProfileName
                         OCTET STRING,
                     onuTcontServiceProfileTcontType
                         INTEGER,   
                     onuTcontServiceProfileFir    
                         INTEGER,   
                     onuTcontServiceProfileCir    
                         INTEGER,   
                     onuTcontServiceProfilePir    
                         INTEGER, 
                     onuTcontServiceProfileRowStatus
                         RowStatus,
                     onuTcontServiceProfileOnuSchedulerPolicy
                         INTEGER,
                     onuTcontServiceProfileOnuSchedulerWeight
                         OCTET STRING                                                   
                 }

          onuTcontServiceProfileIndex OBJECT-TYPE
              SYNTAX  INTEGER
              ACCESS  read-only
              STATUS  mandatory

              DESCRIPTION
                      "Index of the table, ONU VLAN T-CONT service profile INDEX ."
              ::= { onuTCONTServiceProfileEntry 1 }
                 
          onuTcontServiceProfileName OBJECT-TYPE
              SYNTAX  OCTET STRING
              ACCESS  read-write
              STATUS  mandatory

              DESCRIPTION
                      "ONU VLAN T-CONT service profile Name ."
              ::= { onuTCONTServiceProfileEntry 2 }
                 
          onuTcontServiceProfileTcontType OBJECT-TYPE
              SYNTAX  INTEGER{
                              t-cont-type1(1),
                              t-cont-type2(2),
                              t-cont-type3(3),
                              t-cont-type4(4),
                              t-cont-type5(5)                              
                              }
              ACCESS  read-write
              STATUS  mandatory

              DESCRIPTION
                      "Traffic type which is equivalent to T-CONT type: 1 T-CONT type 1, 2 T-CONT type 2, 3 T-CONT type 3, 
                      4 T-CONT type 4, 5 T-CONT type 5. Default value is 1."
              ::= { onuTCONTServiceProfileEntry 3 }
                 
          onuTcontServiceProfileFir OBJECT-TYPE
              SYNTAX  INTEGER(256..830976)  
              ACCESS  read-write
              STATUS  mandatory

              DESCRIPTION
                      "Fixed bandwidth. The unit is Kbps. Range of allowed values, 256 –830976.Using in type 1 and type 5."
              ::= { onuTCONTServiceProfileEntry 4 }
                 
          onuTcontServiceProfileCir OBJECT-TYPE
              SYNTAX  INTEGER(256..1238272)  
              ACCESS  read-write
              STATUS  mandatory

              DESCRIPTION
                      "Assured bandwidth. The unit is Kbps. Range of allowed values, 256 – 1238272. Using in type 2,type 3 and type 5."
              ::= { onuTCONTServiceProfileEntry 5 }
                 
          onuTcontServiceProfilePir OBJECT-TYPE
              SYNTAX  INTEGER(512..1244160)  
              ACCESS  read-write
              STATUS  mandatory

              DESCRIPTION
                      "Maximum bandwidth. The unit is Kbps. Range of allowed values, 512 – 1244160. Using in type 3,type 4 
                      and type 5. TCONT"
              ::= { onuTCONTServiceProfileEntry 6 }
          
          onuTcontServiceProfileOnuSchedulerPolicy OBJECT-TYPE
              SYNTAX  INTEGER{
                                sp(1),
                                wrr(2)
                             }  
              ACCESS  read-write
              STATUS  mandatory

              DESCRIPTION
                      "Config cos priority queue scheduler policy.1--SP,2--WRR."
              ::= { onuTCONTServiceProfileEntry 8 }
          
          onuTcontServiceProfileOnuSchedulerWeight OBJECT-TYPE
              SYNTAX  OCTET STRING  
              ACCESS  read-write
              STATUS  mandatory

              DESCRIPTION
                      "Config cos queue weight(0-100).For example 1,1,1,1,1,1,1,1."
              ::= { onuTCONTServiceProfileEntry 9 }

          onuTcontServiceProfileRowStatus OBJECT-TYPE
              SYNTAX  RowStatus
              ACCESS  read-create
              STATUS  mandatory

              DESCRIPTION
                      ""
              ::= { onuTCONTServiceProfileEntry 7 }

--  ONU 带宽管理表

             onuBandwidthProfileTable OBJECT-TYPE
                 SYNTAX  SEQUENCE OF OnuBandwidthProfileEntry
                 ACCESS  not-accessible
                 STATUS  mandatory
                 DESCRIPTION
                          "Onu Bandwidth Profile table."
                 ::= { nmsGponProfile 3 }

             onuBandwidthProfileEntry OBJECT-TYPE
                 SYNTAX OnuBandwidthProfileEntry
                 ACCESS  not-accessible
                 STATUS  mandatory
                 DESCRIPTION
                          "Onu Bandwidth Profile entry."
                 INDEX { onuBandwidthProfileIndex }
             ::= { onuBandwidthProfileTable 1 }

             OnuBandwidthProfileEntry ::=
                 SEQUENCE {
                     onuBandwidthProfileIndex
                         INTEGER,
                     onuBandwidthProfileName
                         OCTET STRING,
                     onuBandwidthProfileTcontType
                         INTEGER,   
                     onuBandwidthProfileFixedBandwidth 
                         INTEGER,
                     onuBandwidthProfileAssuredBandwidth  
                         INTEGER,
                     onuBandwidthProfileMaximumBandwidth 
                         INTEGER,
                     onuBandwidthProfileRowStatus
                         RowStatus                      
                 }

          onuBandwidthProfileIndex OBJECT-TYPE
              SYNTAX  INTEGER
              ACCESS  read-only
              STATUS  mandatory

              DESCRIPTION
                      "Index of the table, ONU Bandwidth Profile INDEX ."
              ::= { onuBandwidthProfileEntry 1 }
                 
          onuBandwidthProfileName OBJECT-TYPE
              SYNTAX  OCTET STRING
              ACCESS  read-write
              STATUS  mandatory

              DESCRIPTION
                      "ONU Bandwidth Profile name ."
              ::= { onuBandwidthProfileEntry 2 }
                 
                 
          onuBandwidthProfileTcontType OBJECT-TYPE
              SYNTAX  INTEGER{
                        type1(1),
                        type2(2),
                        type3(3),
                        type4(4),
                        type5(5)
                              }
              ACCESS  read-write
              STATUS  mandatory

              DESCRIPTION
                      "Traffic type which is equivalent to T-CONT type: 1 T-CONT type 1,2 T-CONT type 2,3 T-CONT type 3,
                      4 T-CONT type 4, 5 T-CONT type 5."
              ::= { onuBandwidthProfileEntry 3 }
                 
          onuBandwidthProfileFixedBandwidth OBJECT-TYPE
              SYNTAX  INTEGER(128..2500000)
              ACCESS  read-write
              STATUS  mandatory

              DESCRIPTION
                      "Fixed bandwidth, the granularity is 64Kbps. The unit is Kbps. Range of allowed values, 128 –2500000. Default value is 128Kbps."
              ::= { onuBandwidthProfileEntry 4 }
                 
          onuBandwidthProfileAssuredBandwidth OBJECT-TYPE
              SYNTAX  INTEGER(0..2500000)
              ACCESS  read-write
              STATUS  mandatory

              DESCRIPTION
                      "Assured bandwidth, the granularity is 64Kbps. The unit is Kbps. Range of allowed values, 0, 256 – 2500000. Not Valid for Type 1
                       TCONT. Default value is 0."
              ::= { onuBandwidthProfileEntry 5 }
                 
          onuBandwidthProfileMaximumBandwidth OBJECT-TYPE
              SYNTAX  INTEGER(128..2500000)
              ACCESS  read-write
              STATUS  mandatory

              DESCRIPTION
                      "Maximum bandwidth, the granularity is 64Kbps. The unit is Kbps. Range of allowed values, 128 – 2500000. Not valid for Type 1 
                      TCONT. Default value is 1024."
              ::= { onuBandwidthProfileEntry 6 }
                 
          onuBandwidthProfileRowStatus OBJECT-TYPE
              SYNTAX  RowStatus
              ACCESS  read-create
              STATUS  mandatory

              DESCRIPTION
                      ""
              ::= { onuBandwidthProfileEntry 7 }

-- ONU T-CONT与虚端口绑定管理表

             onuTcontVirportBindProfileTable OBJECT-TYPE
                 SYNTAX  SEQUENCE OF OnuTcontVirportBindProfileEntry
                 ACCESS  not-accessible
                 STATUS  mandatory
                 DESCRIPTION
                          "Onu Tcont Virport Bind Profile table."
                 ::= { nmsGponProfile 4 }

             onuTcontVirportBindProfileEntry OBJECT-TYPE
                 SYNTAX OnuTcontVirportBindProfileEntry
                 ACCESS  not-accessible
                 STATUS  mandatory
                 DESCRIPTION
                          "Onu Tcont Virport Bind Profile entry."
                 INDEX { onuTcontVirportBindProfileIndex }
             ::= { onuTcontVirportBindProfileTable 1 }

             OnuTcontVirportBindProfileEntry ::=
                 SEQUENCE {
                     onuTcontVirportBindProfileIndex
                         INTEGER,
                     onuTcontVirportBindProfileVirportIndex  
                         INTEGER,
                     onuTcontVirportBindProfileName
                         OCTET STRING,
                     onuTcontVirportBindProfileTcontID
                         INTEGER,   
                     onuTcontVirportBindProfileTcontServiceProfileID 
                         INTEGER,
                     onuTcontVirportBindProfileVirportServiceProfileID 
                         INTEGER,
                     onuTcontVirportBindProfileRowStatus
                         RowStatus                      
                 }

          onuTcontVirportBindProfileIndex OBJECT-TYPE
              SYNTAX  INTEGER
              ACCESS  read-only
              STATUS  mandatory
              DESCRIPTION
                      "Index of the table, ONU Tcont Virport Bind Profile INDEX ."
              ::= { onuTcontVirportBindProfileEntry 1 }
                 
          onuTcontVirportBindProfileVirportIndex OBJECT-TYPE
              SYNTAX  INTEGER
              ACCESS  read-only
              STATUS  mandatory
              DESCRIPTION
                      "Virtual port index from ONU’s perspective. Default value is 1."
              ::= { onuTcontVirportBindProfileEntry 2 }
                 
          onuTcontVirportBindProfileName OBJECT-TYPE
              SYNTAX  OCTET STRING
              ACCESS  read-write
              STATUS  mandatory
              DESCRIPTION
                      "ONU Tcont Virport Bind Profile name ."
              ::= { onuTcontVirportBindProfileEntry 3 }
                 
          onuTcontVirportBindProfileTcontID OBJECT-TYPE
              SYNTAX  INTEGER
              ACCESS  read-write
              STATUS  mandatory
              DESCRIPTION
                      "T-CONT index from ONU’s perspective. Default value is 1."
              ::= { onuTcontVirportBindProfileEntry 4 }
                 
          onuTcontVirportBindProfileTcontServiceProfileID OBJECT-TYPE
              SYNTAX  INTEGER
              ACCESS  read-write
              STATUS  mandatory
              DESCRIPTION
                      "It points to the associated ONU T-CONT service profile. Default value is 1."
              ::= { onuTcontVirportBindProfileEntry 5 }
                 
          onuTcontVirportBindProfileVirportServiceProfileID OBJECT-TYPE
              SYNTAX  INTEGER
              ACCESS  read-write
              STATUS  mandatory
              DESCRIPTION
                      "It points to the associated ONU virtual port service profile. Default value is 1."
              ::= { onuTcontVirportBindProfileEntry 6 }
                 
          onuTcontVirportBindProfileRowStatus OBJECT-TYPE
              SYNTAX  RowStatus
              ACCESS  read-create
              STATUS  mandatory

              DESCRIPTION
                      ""
              ::= { onuTcontVirportBindProfileEntry 7 }

-- ONU虚端口管理表              

             onuVirtualPortServiceProfileTable OBJECT-TYPE
                 SYNTAX  SEQUENCE OF OnuVirtualPortServiceProfileEntry
                 ACCESS  not-accessible
                 STATUS  mandatory
                 DESCRIPTION
                          "Onu Virtual Port Service Profile table."
                 ::= { nmsGponProfile 5 }

             onuVirtualPortServiceProfileEntry OBJECT-TYPE
                 SYNTAX OnuVirtualPortServiceProfileEntry
                 ACCESS  not-accessible
                 STATUS  mandatory
                 DESCRIPTION
                          "Onu Virtual Port Service Profile entry."
                 INDEX { onuVirportProfileIndex }
             ::= { onuVirtualPortServiceProfileTable 1 }

             OnuVirtualPortServiceProfileEntry ::=
                 SEQUENCE {
                     onuVirportProfileIndex
                         INTEGER,
                     onuVirportProfileName
                         OCTET STRING,
                     onuVirportProfileUsTrafficMapType 
                         INTEGER,
                     onuVirportProfileTypeOfService  
                         INTEGER,
                     onuVirportProfileEncrypMode 
                         INTEGER,
                     onuVirportProfileUsBwProID
                         INTEGER,   
                     onuVirportProfileUsFlowPriority
                         INTEGER,   
                     onuVirportProfileUsFlowWeight
                         INTEGER,   
                     onuVirportProfileUsRateCtlSchedulerProID
                         INTEGER,   
                     onuVirportProfileDsBwProID
                         INTEGER,   
                     onuVirportProfileDsQueueSchType
                         INTEGER,   
                     onuVirportProfileDsFlowPriority
                         INTEGER,   
                     onuVirportProfileRowStatus
                         RowStatus,
                     onuVirportProfileOltDsQueue
                         INTEGER
                 }

          onuVirportProfileIndex OBJECT-TYPE
              SYNTAX  INTEGER
              ACCESS  read-only
              STATUS  mandatory
              DESCRIPTION
                      "Index of the table, ONU Virtual Port Service Profile INDEX ."
              ::= { onuVirtualPortServiceProfileEntry 1 }
                 
          onuVirportProfileName OBJECT-TYPE
              SYNTAX  OCTET STRING
              ACCESS  read-write
              STATUS  mandatory
              DESCRIPTION
                      "ONU Virtual Port Service Profile Name ."
              ::= { onuVirtualPortServiceProfileEntry 2 }
                 
          onuVirportProfileUsTrafficMapType OBJECT-TYPE
              SYNTAX  INTEGER
              ACCESS  read-only
              STATUS  mandatory
              DESCRIPTION
                      "pstream traffic mapping type is inherited from the upstreamTrafficMappingType of its ONU/ONT."
              ::= { onuVirtualPortServiceProfileEntry 3 }
                 
          onuVirportProfileTypeOfService OBJECT-TYPE
              SYNTAX  INTEGER{
                              data(1),
                              iptv(2),
                              video-on-demand(3),
                              voip(4),
                              ti(5),
                              e1(6),
                              hpna(7),
                              others(8)
                              }
              ACCESS  read-write
              STATUS  mandatory
              DESCRIPTION
                      "Type of service for which this virtual port is to be used: 1 Data, 2 IPTV, 3 Video-on-demand, 4 VoIP, 
                      5 T1, 6 E1, 7 HPNA, 8 Others. Default value is 1."
              ::= { onuVirtualPortServiceProfileEntry 4 }
                 
          onuVirportProfileEncrypMode OBJECT-TYPE
              SYNTAX  INTEGER{
                              enable(1),
                              disable(2)       
                             }
              ACCESS  read-write
              STATUS  mandatory
              DESCRIPTION
                      "Encryption mode: 1 Enabled, 2 Disabled. Default value is 2."
              ::= { onuVirtualPortServiceProfileEntry 5 }   
                 
          onuVirportProfileUsBwProID OBJECT-TYPE
              SYNTAX  INTEGER
              ACCESS  read-write
              STATUS  mandatory
              DESCRIPTION
                      "It points to the associated ONU bandwidth profile for upstream."
              ::= { onuVirtualPortServiceProfileEntry 6 }   
                 
          onuVirportProfileUsFlowPriority OBJECT-TYPE
              SYNTAX  INTEGER(1..8)
              ACCESS  read-write
              STATUS  mandatory
              DESCRIPTION
                      "It’s valid only in either flow-based priority-controlled or flow-based priority-and-rate-
               controlled upstream queuing and scheduling type. Valid range 1 - 8.Default value is 8. "
              ::= { onuVirtualPortServiceProfileEntry 7 }   
                 
          onuVirportProfileUsFlowWeight OBJECT-TYPE
              SYNTAX  INTEGER(0..255)
              ACCESS  read-write
              STATUS  mandatory
              DESCRIPTION
                      "It’s valid only in flow-based rate-controlled queuing and scheduling type. Valid range 0-255.
                      Default value is 1. "
              ::= { onuVirtualPortServiceProfileEntry 8 }   
                 
          onuVirportProfileUsRateCtlSchedulerProID OBJECT-TYPE
              SYNTAX  INTEGER
              ACCESS  read-write
              STATUS  mandatory
              DESCRIPTION
                      "It points to the associated ONU upstream rate-control scheduler profile which exist. Default value 
                      is 1."
              ::= { onuVirtualPortServiceProfileEntry 9 }   
                 
          onuVirportProfileDsBwProID OBJECT-TYPE
              SYNTAX  INTEGER
              ACCESS  read-write
              STATUS  mandatory
              DESCRIPTION
                      "It points to the associated ONU bandwidth profile for downstream. Default value is 1."
              ::= { onuVirtualPortServiceProfileEntry 10 }  
                 
          onuVirportProfileDsQueueSchType OBJECT-TYPE
              SYNTAX  INTEGER{
                              priority-controlled(0),
                              flow-based-priority-controlled(1)       
                             }
              ACCESS  read-write
              STATUS  mandatory
              DESCRIPTION
                      "0 – Priority Controlled. 1 - Flow-based priority-controlled. Default value is 1."
              ::= { onuVirtualPortServiceProfileEntry 11 }   
              
          onuVirportProfileDsFlowPriority OBJECT-TYPE
              SYNTAX  INTEGER(1..8)
              ACCESS  read-write
              STATUS  mandatory
              DESCRIPTION
                      "It’s valid only in flow-based priority-controlled downstream queuing and scheduling type. 
                      Valid range 1 - 8. Default value is 8. "
              ::= { onuVirtualPortServiceProfileEntry 12 }  
              
          onuVirportProfileRowStatus OBJECT-TYPE
              SYNTAX  RowStatus
              ACCESS  read-create
              STATUS  mandatory

              DESCRIPTION
                      ""
              ::= { onuVirtualPortServiceProfileEntry 13 }

          onuVirportProfileOltDsQueue OBJECT-TYPE
              SYNTAX  INTEGER(1..4)
              ACCESS  read-write
              STATUS  mandatory
              DESCRIPTION
                      "Specifies virtualport downstream queue when olt enabled onu-based scheduler.
                      Valid range 1 - 4. Default value is 1. "
              ::= { onuVirtualPortServiceProfileEntry 14 }  
              
-- ONU流量管理表
                 
             onuFlowProfileTable OBJECT-TYPE
                 SYNTAX  SEQUENCE OF OnuFlowProfileEntry
                 ACCESS  not-accessible
                 STATUS  mandatory
                 DESCRIPTION
                          "Onu flow Profile table."
                 ::= { nmsGponProfile 6 }

             onuFlowProfileEntry OBJECT-TYPE
                 SYNTAX OnuFlowProfileEntry
                 ACCESS  not-accessible
                 STATUS  mandatory
                 DESCRIPTION
                          "Onu flow profile entry."
                 INDEX { onuFlowProfileIndex1,onuFlowProfileIndex2 }
             ::= { onuFlowProfileTable 1 }

             OnuFlowProfileEntry ::=
                 SEQUENCE {
                     onuFlowProfileIndex1
                         INTEGER,
                     onuFlowProfileIndex2
                         INTEGER,
                     onuFlowProfileName 
                         OCTET STRING,
                     onuFlowProfileUniType  
                         INTEGER,
                     onuFlowProfileUniPortBitMap 
                         INTEGER,
                     onuFlowProfileUsMapType
                         INTEGER,   
                     onuFlowProfileVlanIdStart
                         INTEGER,   
                     onuFlowProfileVlanIdStop
                         INTEGER,   
                     onuFlowProfilePBITsMap
                         INTEGER,   
                     onuFlowProfileVirportNo
                         INTEGER,   
                     onuFlowProfileRowStatus
                         RowStatus,
                     onuFlowProfileVlanIdList
                         OCTET STRING,
                     onuFlowProfileDsBandwidth
                         INTEGER,
                     onuFlowProfileStormCtrl
                         INTEGER,
                     onuFlowProfileVlanIdStep
                         INTEGER   
                 }

          onuFlowProfileIndex1 OBJECT-TYPE
              SYNTAX  INTEGER
              ACCESS  read-only
              STATUS  mandatory
              DESCRIPTION
                      "Index of the table, ONU flow Profile INDEX 1."
              ::= { onuFlowProfileEntry 1 }
                 
          onuFlowProfileIndex2 OBJECT-TYPE
              SYNTAX  INTEGER
              ACCESS  read-only
              STATUS  mandatory
              DESCRIPTION
                      "Index of the table, ONU flow Profile INDEX 2."
              ::= { onuFlowProfileEntry 2 }
                 
          onuFlowProfileName OBJECT-TYPE
              SYNTAX  OCTET STRING
              ACCESS  read-write
              STATUS  mandatory
              DESCRIPTION
                      "IONU flow Profile name."
              ::= { onuFlowProfileEntry 3 }
                 
          onuFlowProfileUniType OBJECT-TYPE
              SYNTAX  INTEGER{
                        ethernet-uni(1),
                        pots-uni(2),
                        t1(3),
                        e1(4),
                        hpna(5),
                        ip-host(6)
                              }
              ACCESS  read-write
              STATUS  mandatory
              DESCRIPTION
                      "Physical port type: 1 Ethernet UNI, 2 POTS UNI, 3 T1, 4 E1, 5 HPNA, 6 IP Host. Default value is 1."
              ::= { onuFlowProfileEntry 4 }
                 
          onuFlowProfileUniPortBitMap OBJECT-TYPE
              SYNTAX  INTEGER
              ACCESS  read-write
              STATUS  mandatory
              DESCRIPTION
                      "UNI Port bit map representing 1 or more UNI ports to be associated with a flow. If the value is set
                       to 1, it would mean UNI port 1, if the value is set to 2, it would mean UNI port 2, if the value is 
                       set to 3, it would mean, both UNI port 1 and 2. The value 255 would mean, UNI port 1 through 7. The 
                       value 0 will indicate the flow applies to all UNI ports of the ONU."
              ::= { onuFlowProfileEntry 5 }
                 
          onuFlowProfileUsMapType OBJECT-TYPE
              SYNTAX  INTEGER{
                        user-port(1),
                        vlan-id(2),
                        pbit(3),
                        vlan-id-pbit(4),
                        ehter-type(5),
                        dscp(6),
                        user-port-pbits(7),
                        user-port-dscp(8)
                              }
              ACCESS  read-write
              STATUS  mandatory
              DESCRIPTION
                      "Upstream Traffic Mapping mechanism: 1 User Port, 2 VLAN ID, 3 PBIT, 4 VLAN ID + PBIT, 5 Ether Type, 
                      6 DSCP, 7 User Port + PBITS, 8 User Port + DSCP, The valid values are 1 to 4. Values 5, 6, 7 and 8 
                      are reserved for future use. Default value is 2."
              ::= { onuFlowProfileEntry 6 }
                 
          onuFlowProfileVlanIdStart OBJECT-TYPE
              SYNTAX  INTEGER(1..4095)
              ACCESS  read-write
              STATUS  mandatory
              DESCRIPTION
                      "The beginning of the VLAN Id range to be mapped to the flow. 1..4095."
              ::= { onuFlowProfileEntry 7 }
                 
          onuFlowProfileVlanIdStop OBJECT-TYPE
              SYNTAX  INTEGER(1..4095)
              ACCESS  read-write
              STATUS  mandatory
              DESCRIPTION
                      "The end of the VLAN Id range. 1..4095. VLAN ID Stop–VLAN ID Start should be less than equal to 
                      12 for 1 flow."
              ::= { onuFlowProfileEntry 8 }
                 
          onuFlowProfilePBITsMap OBJECT-TYPE
              SYNTAX  INTEGER
              ACCESS  read-write
              STATUS  mandatory
              DESCRIPTION
                      "Bit map representing PBITs that have to be mapped to the flow. If the value is set to 1, it would 
                      mean PBIT 0, if the value is set to 2, it would mean PBIT 1, if the value is set to 3, it would 
                      mean, both PBIT 0 and 1. The value 255 would mean, PBITS 0 through 7. "
              ::= { onuFlowProfileEntry 9 }
                 
          onuFlowProfileVirportNo OBJECT-TYPE
              SYNTAX  INTEGER
              ACCESS  read-write
              STATUS  mandatory
              DESCRIPTION
                      "ONU flow profile virtual port number."
              ::= { onuFlowProfileEntry 10 }
                 
          onuFlowProfileRowStatus OBJECT-TYPE
              SYNTAX  RowStatus
              ACCESS  read-create
              STATUS  mandatory

              DESCRIPTION
                      ""
              ::= { onuFlowProfileEntry 11 }

          onuFlowProfileVlanIdList OBJECT-TYPE
              SYNTAX  OCTET STRING
              ACCESS  read-write
              STATUS  mandatory
              DESCRIPTION
                      "VLAN list such as (1,3,5,7) Or (1,3-5,7) Or (1-7), up to 12 entry."
              ::= { onuFlowProfileEntry 12 }

          onuFlowProfileDsBandwidth OBJECT-TYPE
              SYNTAX  INTEGER
              ACCESS  read-write
              STATUS  mandatory
              DESCRIPTION
                      "ONU downstream bandwidth.(unit:64kbps)"
              ::= { onuFlowProfileEntry 13 }
                 
          onuFlowProfileStormCtrl OBJECT-TYPE
              SYNTAX  INTEGER
              ACCESS  read-write
              STATUS  mandatory
              DESCRIPTION
                      "ONU upstream traffic control."
              ::= { onuFlowProfileEntry 14 }

          onuFlowProfileVlanIdStep OBJECT-TYPE
              SYNTAX  INTEGER
              ACCESS  read-write
              STATUS  mandatory
              DESCRIPTION
                      "VlanId step length based on onu sequence."
              ::= { onuFlowProfileEntry 15 }

-- ONU速率控制管理表

             onuRateControlSchedulerProfileTable OBJECT-TYPE
                 SYNTAX  SEQUENCE OF OnuRateControlSchedulerProfileEntry
                 ACCESS  not-accessible
                 STATUS  mandatory
                 DESCRIPTION
                          "Onu rate control scheduler profile table."
                 ::= { nmsGponProfile 7 }

             onuRateControlSchedulerProfileEntry OBJECT-TYPE
                 SYNTAX OnuRateControlSchedulerProfileEntry
                 ACCESS  not-accessible
                 STATUS  mandatory
                 DESCRIPTION
                          "Onu rate control scheduler profile entry."
                 INDEX { onuRateCtlProfileIndex }
             ::= { onuRateControlSchedulerProfileTable 1 }

             OnuRateControlSchedulerProfileEntry ::=
                 SEQUENCE {
                     onuRateCtlProfileIndex
                         INTEGER,
                     onuRateCtlProfileName 
                         OCTET STRING,
                     onuRateCtlProfileCir  
                         INTEGER,
                     onuRateCtlProfilePir 
                         INTEGER,
                     onuRateCtlProfileScheduleWeight
                         INTEGER,   
                     onuRateCtlProfileRowStatus
                         RowStatus                      
                 }

          onuRateCtlProfileIndex OBJECT-TYPE
              SYNTAX  INTEGER
              ACCESS  read-only
              STATUS  mandatory
              DESCRIPTION
                      "Index of the table, ONU rate control scheduler profile INDEX 1."
              ::= { onuRateControlSchedulerProfileEntry 1 }
                 
          onuRateCtlProfileName OBJECT-TYPE
              SYNTAX  OCTET STRING
              ACCESS  read-write
              STATUS  mandatory
              DESCRIPTION
                      "ONU rate control scheduler profile name."
              ::= { onuRateControlSchedulerProfileEntry 2 }
                 
          onuRateCtlProfileCir OBJECT-TYPE
              SYNTAX  INTEGER
              ACCESS  read-write
              STATUS  mandatory
              DESCRIPTION
                      "CIR, the granularity is 64Kbps. The unit is Kbps. Range of allowed values, 256 – PIR. "
              ::= { onuRateControlSchedulerProfileEntry 3 }
                 
          onuRateCtlProfilePir OBJECT-TYPE
              SYNTAX  INTEGER(128..2500000)
              ACCESS  read-write
              STATUS  mandatory
              DESCRIPTION
                      "PIR, the granularity is 64Kbps. The unit is Kbps. Range of allowed values, CIR – 1244160.  "
              ::= { onuRateControlSchedulerProfileEntry 4 }
                 
          onuRateCtlProfileScheduleWeight OBJECT-TYPE
              SYNTAX  INTEGER(0..255)
              ACCESS  read-write
              STATUS  mandatory
              DESCRIPTION
                      "Scheduler weight. Valid range 0-255. Default value is 1. "
              ::= { onuRateControlSchedulerProfileEntry 5 }
                 
          onuRateCtlProfileRowStatus OBJECT-TYPE
              SYNTAX  RowStatus
              ACCESS  read-create
              STATUS  mandatory
              DESCRIPTION
                      ""
              ::= { onuRateControlSchedulerProfileEntry 6 }
                 
-- UNI端口配置Profile表  

             onuEthernetUNIConfigProfileTable OBJECT-TYPE
                 SYNTAX  SEQUENCE OF OnuEthernetUNIConfigProfileEntry
                 ACCESS  not-accessible
                 STATUS  mandatory
                 DESCRIPTION
                          "Onu Ethernet UNI configuration profile table."
                 ::= { nmsGponProfile 8 }

             onuEthernetUNIConfigProfileEntry OBJECT-TYPE
                 SYNTAX OnuEthernetUNIConfigProfileEntry
                 ACCESS  not-accessible
                 STATUS  mandatory
                 DESCRIPTION
                          "Onu Ethernet UNI configuration profile entry."
                 INDEX { onuEthernetUNIPortProfileIndex }
             ::= { onuEthernetUNIConfigProfileTable 1 }

             OnuEthernetUNIConfigProfileEntry ::=
                 SEQUENCE {
                     onuEthernetUNIPortProfileIndex
                         INTEGER,
                     onuEthernetUNIPortProfileName 
                         OCTET STRING,
                     onuEthernetUNIPortAutoNegotiation  
                         INTEGER,
                     onuEthernetUNIPortSpeed 
                         INTEGER,
                     onuEthernetUNIPortDuplex
                         INTEGER,   
                     onuEthernetUNIPortExpectedType
                         INTEGER,   
                     onuEthernetUNIPortMaxFrameSize
                         INTEGER,   
                     onuEthernetUNIPortEthernetInterfaceWiring
                         INTEGER,
                     onuEthernetUNIPortProfileRowStatus
                         RowStatus,
                     onuEthernetUNIPortSchedulerPolicy
                         INTEGER,   
                     onuEthernetUNIPortSchedulerWeight
                         OCTET STRING,
                     onuEthernetUNIPortPoeItuEnable
                         INTEGER,
                     onuEthernetUNIPortPoeItuPowerPairPinout
                         INTEGER,
                     onuEthernetUNIPortPoeItuPowerPri
                         INTEGER,   
                     onuEthernetUNIPortPoeItuPseClass
                         INTEGER                          
                 }

          onuEthernetUNIPortProfileIndex OBJECT-TYPE
              SYNTAX  INTEGER
              ACCESS  read-only
              STATUS  mandatory
              DESCRIPTION
                      "Index of the table, ONU Ethernet UNI configuration profile INDEX 1."
              ::= { onuEthernetUNIConfigProfileEntry 1 }
                 
          onuEthernetUNIPortProfileName OBJECT-TYPE
              SYNTAX  OCTET STRING
              ACCESS  read-write
              STATUS  mandatory
              DESCRIPTION
                      "ONU Ethernet UNI configuration profile name."
              ::= { onuEthernetUNIConfigProfileEntry 2 }
                 
          onuEthernetUNIPortAutoNegotiation OBJECT-TYPE
              SYNTAX  INTEGER{
                        enable(1),
                        disable(2)
                        }
              ACCESS  read-write
              STATUS  mandatory
              DESCRIPTION
                      "Auto negotiation: 1 Enabled, 2 Disabled. Default value is 1. "
              ::= { onuEthernetUNIConfigProfileEntry 3 }
                 
          onuEthernetUNIPortSpeed OBJECT-TYPE
              SYNTAX  INTEGER{
                        auto(0),
                        s10Mbps(1),
                        s100Mbps(2),
                        s1000Mbps(3)
                        }
              ACCESS  read-write
              STATUS  mandatory
              DESCRIPTION
                      "Speed:0 auto, 1 10Mbps, 2 100Mbps, 3 1000Mbps. Default value is 0. "
              ::= { onuEthernetUNIConfigProfileEntry 4 }
                 
          onuEthernetUNIPortDuplex OBJECT-TYPE
              SYNTAX  INTEGER{
                        auto(0),
                        full(1),
                        half(2)
                        }
              ACCESS  read-write
              STATUS  mandatory
              DESCRIPTION
                      "Duplex: 1 Full, 2 Half. Default value is 0. "
              ::= { onuEthernetUNIConfigProfileEntry 5 }
                 
          onuEthernetUNIPortExpectedType OBJECT-TYPE
              SYNTAX  INTEGER
              ACCESS  read-write
              STATUS  mandatory
              DESCRIPTION
                      "This attribute supports pre-provisioning. It is coded as follows: 1 Autosense, 2 to 254 is compatible 
                      with other Ethernet circuit pack type Upon ME instantiation, the ONT sets this attribute to 0. Default value is 1. "
              ::= { onuEthernetUNIConfigProfileEntry 6 }
                 
          onuEthernetUNIPortMaxFrameSize OBJECT-TYPE
              SYNTAX  INTEGER(1500..2048)
              ACCESS  read-write
              STATUS  mandatory
              DESCRIPTION
                      "This attribute denotes the maximum frame size allowed across this interface.Range 1500-2048.Defult is 1518."
              ::= { onuEthernetUNIConfigProfileEntry 7 }
                 
          onuEthernetUNIPortEthernetInterfaceWiring OBJECT-TYPE
              SYNTAX  INTEGER{
                        dce(0),
                        dte(1),
                        auto(2)
                        }
              ACCESS  read-write
              STATUS  mandatory
              DESCRIPTION
                      "This attribute specifies the Ethernet interface wiring: 1 DCE (default), 2 DTE. Default value is 1. "
              ::= { onuEthernetUNIConfigProfileEntry 8 }
          
          onuEthernetUNIPortSchedulerPolicy OBJECT-TYPE
              SYNTAX  INTEGER{
                        not-assigned(0),
                        sp(1),
                        wrr(2),
                        }
              ACCESS  read-write
              STATUS  mandatory
              DESCRIPTION
                      "Config cos priority queue scheduler policy: 0 not-assigned, 1 SP, 2 WRR."
              ::= { onuEthernetUNIConfigProfileEntry 10 }
          
          onuEthernetUNIPortSchedulerWeight OBJECT-TYPE
              SYNTAX  OCTET STRING 
              ACCESS  read-create
              STATUS  mandatory
              DESCRIPTION
                      "Config cos queue weight(0-100).For example 1,1,1,1,1,1,1,1"
              ::= { onuEthernetUNIConfigProfileEntry 11 }  
          
          onuEthernetUNIPortPoeItuEnable OBJECT-TYPE
              SYNTAX  INTEGER{
                                enable(1),
                                disable(2)
                            }
              ACCESS  read-write
              STATUS  mandatory
              DESCRIPTION
                      "Config Poe power control:0 disable, 1 enable."
              ::= { onuEthernetUNIConfigProfileEntry 12 }
                 
          onuEthernetUNIPortPoeItuPowerPairPinout OBJECT-TYPE
              SYNTAX  INTEGER{
                                none(0),
                                signal(1),
                                spare(2)
                             }
              ACCESS  read-write
              STATUS  mandatory
              DESCRIPTION
                      "Config poe power pair pinout. "
              ::= { onuEthernetUNIConfigProfileEntry 13 }
          
          onuEthernetUNIPortPoeItuPowerPri OBJECT-TYPE
              SYNTAX  INTEGER{
                                none(0),
                                critical(1),
                                high(2),
                                low(3)
                             }
              ACCESS  read-write
              STATUS  mandatory
              DESCRIPTION
                      "Config poe power priority."
              ::= { onuEthernetUNIConfigProfileEntry 14 }
          
          onuEthernetUNIPortPoeItuPseClass OBJECT-TYPE
              SYNTAX  INTEGER{
                                class-0(0),
                                class-1(1),
                                class-2(2),
                                class-3(3),
                                class-4(4),
                                default(255)
                                }
              ACCESS  read-create
              STATUS  mandatory
              DESCRIPTION
                      "Config pse Power feed enabled class."
              ::= { onuEthernetUNIConfigProfileEntry 15 }
              
          onuEthernetUNIPortProfileRowStatus OBJECT-TYPE
              SYNTAX  RowStatus
              ACCESS  read-create
              STATUS  mandatory
              DESCRIPTION
                      ""
              ::= { onuEthernetUNIConfigProfileEntry 9 }                  

-- 组播oper profile配置表

            onuMcstOperConfigProfileTable OBJECT-TYPE
                SYNTAX  SEQUENCE OF OnuMcstOperConfigProfileEntry
                ACCESS  not-accessible
                STATUS  mandatory
                DESCRIPTION
                    "A list of  ONU multicast operation config profile table entries."
                ::= { nmsGponProfile 9 }

            onuMcstOperConfigProfileEntry OBJECT-TYPE
                SYNTAX  OnuMcstOperConfigProfileEntry
                ACCESS  not-accessible
                STATUS  mandatory
                DESCRIPTION
                    "A collection of additional objects in the
                        ONU multicast operation config profile table."
                INDEX { onuMcstOperConfigProfileIndex }
                ::= { onuMcstOperConfigProfileTable 1 }

            OnuMcstOperConfigProfileEntry ::=
                SEQUENCE {
                    onuMcstOperConfigProfileIndex
                        INTEGER,
                    onuMcstOperConfigProfileName
                        OCTET STRING,
                    onuMcstGponStandard
                        INTEGER,
                    onuMcstIGMPVersion
                        INTEGER,
                    onuMcstControlMode
                        INTEGER,
                    onuMcstFastLeaveMode
                        INTEGER,
                    onuMcstUpstreamIGMPTCIVlan
                        INTEGER,
                    onuMcstUpstreamIGMPTCIPbits
                        INTEGER,
                    onuMcstUpstreamIGMPTagControl
                        INTEGER,
                    onuMcstMaxSimultaneousGroup
                        INTEGER,
                    onuMcstLastMemberQueryInterval
                        INTEGER,
                    onuMcstTagStrip
                        INTEGER,
                    onuMcstOperProfileRowStatus
                        RowStatus,
                    onuMcstDownstreamIGMPTCIVlan
                        INTEGER,
                    onuMcstDownstreamIGMPTCIPbits
                        INTEGER,
                    onuMcstDownstreamIGMPTagControl
                        INTEGER,
                    onuMcstMaxMcstBandwidth
                        INTEGER
                    }


            onuMcstOperConfigProfileIndex OBJECT-TYPE
                   SYNTAX  INTEGER
                   ACCESS  read-write
                   STATUS  mandatory
                   DESCRIPTION
                           "profile index."
                   ::= { onuMcstOperConfigProfileEntry 1 }

               onuMcstOperConfigProfileName OBJECT-TYPE
                   SYNTAX  OCTET STRING
                   ACCESS  read-write
                   STATUS  mandatory
                   DESCRIPTION
                           "The name of a profile. "
                   ::= { onuMcstOperConfigProfileEntry 2 }

               onuMcstGponStandard OBJECT-TYPE
                   SYNTAX  INTEGER{
                             itu_g988(1),
                             ctc(2)
                                   }
                   ACCESS  read-write
                   STATUS  mandatory
                   DESCRIPTION
                           "Config GPON technical standard:1 -- ITU-G988(defult); 2 -- CTC"
                   ::= { onuMcstOperConfigProfileEntry 3 }

               onuMcstIGMPVersion OBJECT-TYPE
                   SYNTAX  INTEGER
                   ACCESS  read-write
                   STATUS  mandatory
                   DESCRIPTION
                           "Config IGMP Version:1 -- IGMPv1; 2 -- IGMPv2(defult); 3 -- IGMPv3;
                           4-15 Reserced; 16 -- MLDv1; 17 -- MLDv2"
                   ::= { onuMcstOperConfigProfileEntry 4 }

               onuMcstControlMode OBJECT-TYPE
                   SYNTAX  INTEGER{
                             snooping(0),
                             spr(1),
                             proxy(2)
                                   }
                   ACCESS  read-write
                   STATUS  mandatory
                   DESCRIPTION
                           "Config multicast control mode:; 0 -- Snooping(defult); 1 -- SPR; 2 -- Proxy"
                   ::= { onuMcstOperConfigProfileEntry 5 }

               onuMcstFastLeaveMode OBJECT-TYPE
                   SYNTAX  INTEGER{
                             enable(1),
                             disable(2)
                                   }
                   ACCESS  read-write
                   STATUS  mandatory
                   DESCRIPTION
                           "Config fast leave mode: 1 -- enable, 2 -- disable."
                   ::= { onuMcstOperConfigProfileEntry 6 }

               onuMcstUpstreamIGMPTCIVlan OBJECT-TYPE
                   SYNTAX  INTEGER
                   ACCESS  read-write
                   STATUS  mandatory
                   DESCRIPTION
                           "Config upstream IGMP TCI Vlan ID."
                   ::= { onuMcstOperConfigProfileEntry 7 }

               onuMcstUpstreamIGMPTCIPbits OBJECT-TYPE
                   SYNTAX  INTEGER
                   ACCESS  read-write
                   STATUS  mandatory
                   DESCRIPTION
                           "Config upstream IGMP TCI P-bits."
                   ::= { onuMcstOperConfigProfileEntry 8 }

               onuMcstUpstreamIGMPTagControl OBJECT-TYPE
                   SYNTAX  INTEGER{
                             transparent(0),
                             add_tag(1),
                             replace_tag(2),
                             replace_vlan(3)
                                   }
                   ACCESS  read-write
                   STATUS  mandatory
                   DESCRIPTION
                           "Config upstream IGMP tag control mode:0 -- transparent(defult);
                           1 -- add tag; 2 -- replace vlan and pbit; 3 -- replace vlan only"
                   ::= { onuMcstOperConfigProfileEntry 9 }

               onuMcstMaxSimultaneousGroup OBJECT-TYPE
                   SYNTAX  INTEGER(1..128)
                   ACCESS  read-write
                   STATUS  mandatory
                   DESCRIPTION
                           "Config max simultaneous group.(1-128)"
                   ::= { onuMcstOperConfigProfileEntry 10 }

               onuMcstLastMemberQueryInterval OBJECT-TYPE
                   SYNTAX  INTEGER
                   ACCESS  read-write
                   STATUS  mandatory
                   DESCRIPTION
                           "Config last member query interval,unit 0.1s.(1-0xFFFF)"
                   ::= { onuMcstOperConfigProfileEntry 11 }

               onuMcstTagStrip OBJECT-TYPE
                   SYNTAX  INTEGER{
                             enable(1),
                             disable(2)
                                   }
                   ACCESS  read-write
                   STATUS  mandatory
                   DESCRIPTION
                           "Enable or disable striping the outer tag of the downstream multicast traffic.
                           1 -- enable, 2 -- disable."
                   ::= { onuMcstOperConfigProfileEntry 12 }

               onuMcstDownstreamIGMPTCIVlan OBJECT-TYPE
                   SYNTAX  INTEGER
                   ACCESS  read-write
                   STATUS  mandatory
                   DESCRIPTION
                           "Config downstream IGMP TCI Vlan ID."
                   ::= { onuMcstOperConfigProfileEntry 14 }

               onuMcstDownstreamIGMPTCIPbits OBJECT-TYPE
                   SYNTAX  INTEGER
                   ACCESS  read-write
                   STATUS  mandatory
                   DESCRIPTION
                           "Config downstream IGMP TCI P-bits."
                   ::= { onuMcstOperConfigProfileEntry 15 }

               onuMcstDownstreamIGMPTagControl OBJECT-TYPE
                   SYNTAX  INTEGER{
                             transparent(0),
                             strip_tag(1),
                             add_tag(2),
                             replace_tag(3),
                             replace_vlan(4)
                                   }
                   ACCESS  read-write
                   STATUS  mandatory
                   DESCRIPTION
                           "Config downstream IGMP tag control mode:0 -- transparent(defult);
                           1 -- strip tag; 2 -- add tag; 3 -- replace vlan and pbit; 4 -- replace vlan only"
                   ::= { onuMcstOperConfigProfileEntry 16 }

               onuMcstMaxMcstBandwidth OBJECT-TYPE
                   SYNTAX  INTEGER
                   UNITS   "kbps"
                   ACCESS  read-write
                   STATUS  mandatory
                   DESCRIPTION
                           "Config max multicast bandwidth in kbps. 0 -- no bandwidth limit."
                   ::= { onuMcstOperConfigProfileEntry 17 }

               onuMcstOperProfileRowStatus OBJECT-TYPE
                   SYNTAX  RowStatus
                   ACCESS  read-create
                   STATUS  mandatory
                   DESCRIPTION
                           "ONU Mcst Oper Config Profile row status. "
                   ::= { onuMcstOperConfigProfileEntry 13 }

-- 静态组播配置Profile表

               onuSMcstConfigProfileTable OBJECT-TYPE
                   SYNTAX  SEQUENCE OF OnuSMcstConfigProfileEntry
                   ACCESS  not-accessible
                   STATUS  mandatory
                   DESCRIPTION
                            "A list of  ONU multicast operation config profile table entries."
                   ::= { nmsGponProfile 10 }

               onuSMcstConfigProfileEntry OBJECT-TYPE
                   SYNTAX  OnuSMcstConfigProfileEntry
                   ACCESS  not-accessible
                   STATUS  mandatory
                   DESCRIPTION
                            "A collection of additional objects in the
                            ONU multicast operation config profile table."
                   INDEX { onuSMcstConfigProfileIndex1, onuSMcstConfigProfileIndex2}
               ::= { onuSMcstConfigProfileTable 1}

               OnuSMcstConfigProfileEntry ::=
                   SEQUENCE {
                       onuSMcstConfigProfileIndex1
                           INTEGER,
                       onuSMcstConfigProfileIndex2
                           INTEGER,
                       onuSMcstConfigProfileName
                           OCTET STRING,
               onuSMcstGemport
                   INTEGER,
               onuSMcstVlanId
                   INTEGER,
               onuSMcstSourceIpv4Address
                   IpAddress,
               onuSMcstIpv4AddressRangeStart
                   IpAddress,
               onuSMcstIpv4AddressRangeStop
                   IpAddress,
               onuSMcstSourceIpv6Address
                   InetAddressIPv6,
               onuSMcstIpv6AddressRangeStart
                   InetAddressIPv6,
               onuSMcstIpv6AddressRangeStop
                   InetAddressIPv6,
               onuSMcstImputedGroupBandwidth
                   INTEGER,
               onuSMcstPreviewLength
                   INTEGER,
               onuSMcstPreviewRepeatTime
                   INTEGER,
               onuSMcstPreviewRepeatCount
                   INTEGER,
               onuSMcstPreviewResetTime
                   INTEGER,
               onuSMcstProfileRowStatus
                   RowStatus
               }


               onuSMcstConfigProfileIndex1 OBJECT-TYPE
                   SYNTAX  INTEGER
                   ACCESS  read-only
                   STATUS  mandatory
                   DESCRIPTION
                           "profile index ."
                   ::= { onuSMcstConfigProfileEntry 1 }

               onuSMcstConfigProfileIndex2 OBJECT-TYPE
                   SYNTAX  INTEGER
                   ACCESS  read-only
                   STATUS  mandatory
                   DESCRIPTION
                           "Entry index ."
                   ::= { onuSMcstConfigProfileEntry 2 }

               onuSMcstConfigProfileName OBJECT-TYPE
                   SYNTAX  OCTET STRING
                   ACCESS  read-write
                   STATUS  mandatory
                   DESCRIPTION
                           "The name of a profile. "
                   ::= { onuSMcstConfigProfileEntry 3 }

               onuSMcstGemport OBJECT-TYPE
                   SYNTAX  INTEGER
                   ACCESS  read-write
                   STATUS  mandatory
                   DESCRIPTION
                           "Config multicast gemport.(4093-4093)"
                   ::= { onuSMcstConfigProfileEntry 4 }

               onuSMcstVlanId OBJECT-TYPE
                   SYNTAX  INTEGER(1..4094)
                   ACCESS  read-write
                   STATUS  mandatory
                   DESCRIPTION
                           "Config multicast VLAN id.(1-4094)"
                   ::= { onuSMcstConfigProfileEntry 5 }

               onuSMcstSourceIpv4Address OBJECT-TYPE
                   SYNTAX  IpAddress
                   ACCESS  read-write
                   STATUS  mandatory
                   DESCRIPTION
                           "Config source ipv4 address."
                   ::= { onuSMcstConfigProfileEntry 6 }

               onuSMcstIpv4AddressRangeStart OBJECT-TYPE
                   SYNTAX  IpAddress
                   ACCESS  read-write
                   STATUS  mandatory
                   DESCRIPTION
                           "Config start destination ipv4 address."
                   ::= { onuSMcstConfigProfileEntry 7 }

               onuSMcstIpv4AddressRangeStop OBJECT-TYPE
                   SYNTAX  IpAddress
                   ACCESS  read-write
                   STATUS  mandatory
                   DESCRIPTION
                           "Config end destination ipv4 address."
                   ::= { onuSMcstConfigProfileEntry 8 }

               onuSMcstSourceIpv6Address OBJECT-TYPE
                   SYNTAX  InetAddressIPv6
                   ACCESS  read-write
                   STATUS  mandatory
                   DESCRIPTION
                           "Config source ipv6 address."
                   ::= { onuSMcstConfigProfileEntry 9 }

               onuSMcstIpv6AddressRangeStart OBJECT-TYPE
                   SYNTAX  InetAddressIPv6
                   ACCESS  read-write
                   STATUS  mandatory
                   DESCRIPTION
                           "Config start destination ipv6 address."
                   ::= { onuSMcstConfigProfileEntry 10 }

               onuSMcstIpv6AddressRangeStop OBJECT-TYPE
                   SYNTAX  InetAddressIPv6
                   ACCESS  read-write
                   STATUS  mandatory
                   DESCRIPTION
                           "Config end destination ipv6 address."
                   ::= { onuSMcstConfigProfileEntry 11 }

               onuSMcstImputedGroupBandwidth OBJECT-TYPE
                   SYNTAX  INTEGER
                   UNITS   "kbps"
                   ACCESS  read-write
                   STATUS  obsolete
                   DESCRIPTION
                           "Config imputed group bandwidth.(1-1244160)kbps"
                   ::= { onuSMcstConfigProfileEntry 12 }

               onuSMcstPreviewLength OBJECT-TYPE
                   SYNTAX  INTEGER
                   ACCESS  read-write
                   STATUS  obsolete
                   DESCRIPTION
                           "The maximum duration of each preview in seconds."
                   ::= { onuSMcstConfigProfileEntry 13 }

               onuSMcstPreviewRepeatTime OBJECT-TYPE
                   SYNTAX  INTEGER
                   ACCESS  read-write
                   STATUS  obsolete
                   DESCRIPTION
                           "The minimum time in seconds between two previews of a given multicast group."
                   ::= { onuSMcstConfigProfileEntry 14 }

               onuSMcstPreviewRepeatCount OBJECT-TYPE
                   SYNTAX  INTEGER
                   ACCESS  read-write
                   STATUS  obsolete
                   DESCRIPTION
                           "The maximum number of times a given multicast group may be previewed."
                   ::= { onuSMcstConfigProfileEntry 15 }

               onuSMcstPreviewResetTime OBJECT-TYPE
                   SYNTAX  INTEGER
                   ACCESS  read-write
                   STATUS  obsolete
                   DESCRIPTION
                           "The time at which the ONU resets the preview repeat counter(24-hour system)."
                   ::= { onuSMcstConfigProfileEntry 16 }

               onuSMcstProfileRowStatus OBJECT-TYPE
                   SYNTAX  RowStatus
                   ACCESS  read-create
                   STATUS  mandatory
                   DESCRIPTION
                           "onu SMcst Profile Row Status."
                   ::= { onuSMcstConfigProfileEntry 17 }


-- 动态组播配置Profile表

               onuDMcstConfigProfileTable OBJECT-TYPE
                   SYNTAX  SEQUENCE OF OnuDMcstConfigProfileEntry
                   ACCESS  not-accessible
                   STATUS  mandatory
                   DESCRIPTION
                            "A list of  ONU multicast operation config profile table entries."
                   ::= { nmsGponProfile 11 }

               onuDMcstConfigProfileEntry OBJECT-TYPE
                   SYNTAX  OnuDMcstConfigProfileEntry
                   ACCESS  not-accessible
                   STATUS  mandatory
                   DESCRIPTION
                            "A collection of additional objects in the
                            ONU multicast operation config profile table."
                   INDEX { onuDMcstConfigProfileIndex1, onuDMcstConfigProfileIndex2}
               ::= { onuDMcstConfigProfileTable 1}

               OnuDMcstConfigProfileEntry ::=
                   SEQUENCE {
                       onuDMcstConfigProfileIndex1
                           INTEGER,
                       onuDMcstConfigProfileIndex2
                           INTEGER,
                       onuDMcstConfigProfileName
                           OCTET STRING,
               onuDMcstGemport
                   INTEGER,
               onuDMcstVlanId
                   INTEGER,
               onuDMcstSourceIpv4Address
                   IpAddress,
               onuDMcstIpv4AddressRangeStart
                   IpAddress,
               onuDMcstIpv4AddressRangeStop
                   IpAddress,
               onuDMcstSourceIpv6Address
                   InetAddressIPv6,
               onuDMcstIpv6AddressRangeStart
                   InetAddressIPv6,
               onuDMcstIpv6AddressRangeStop
                   InetAddressIPv6,
               onuDMcstImputedGroupBandwidth
                   INTEGER,
               onuDMcstPreviewLength
                   INTEGER,
               onuDMcstPreviewRepeatTime
                   INTEGER,
               onuDMcstPreviewRepeatCount
                   INTEGER,
               onuDMcstPreviewResetTime
                   INTEGER,
               onuDMcstProfileRowStatus
                   RowStatus
               }


               onuDMcstConfigProfileIndex1 OBJECT-TYPE
                   SYNTAX  INTEGER
                   ACCESS  read-only
                   STATUS  mandatory
                   DESCRIPTION
                           "profile index ."
                   ::= { onuDMcstConfigProfileEntry 1 }

               onuDMcstConfigProfileIndex2 OBJECT-TYPE
                   SYNTAX  INTEGER
                   ACCESS  read-only
                   STATUS  mandatory
                   DESCRIPTION
                           "Entry index ."
                   ::= { onuDMcstConfigProfileEntry 2 }

               onuDMcstConfigProfileName OBJECT-TYPE
                   SYNTAX  OCTET STRING
                   ACCESS  read-write
                   STATUS  mandatory
                   DESCRIPTION
                           "The name of a profile. "
                   ::= { onuDMcstConfigProfileEntry 3 }

               onuDMcstGemport OBJECT-TYPE
                   SYNTAX  INTEGER
                   ACCESS  read-write
                   STATUS  mandatory
                   DESCRIPTION
                           "Config multicast gemport.(4093-4093)"
                   ::= { onuDMcstConfigProfileEntry 4 }

               onuDMcstVlanId OBJECT-TYPE
                   SYNTAX  INTEGER(1..4094)
                   ACCESS  read-write
                   STATUS  mandatory
                   DESCRIPTION
                           "Config multicast VLAN id.(1-4094)"
                   ::= { onuDMcstConfigProfileEntry 5 }

               onuDMcstSourceIpv4Address OBJECT-TYPE
                   SYNTAX  IpAddress
                   ACCESS  read-write
                   STATUS  mandatory
                   DESCRIPTION
                           "Config source ipv4 address."
                   ::= { onuDMcstConfigProfileEntry 6 }

               onuDMcstIpv4AddressRangeStart OBJECT-TYPE
                   SYNTAX  IpAddress
                   ACCESS  read-write
                   STATUS  mandatory
                   DESCRIPTION
                           "Config start destination ipv4 address."
                   ::= { onuDMcstConfigProfileEntry 7 }

               onuDMcstIpv4AddressRangeStop OBJECT-TYPE
                   SYNTAX  IpAddress
                   ACCESS  read-write
                   STATUS  mandatory
                   DESCRIPTION
                           "Config end destination ipv4 address."
                   ::= { onuDMcstConfigProfileEntry 8 }

               onuDMcstSourceIpv6Address OBJECT-TYPE
                   SYNTAX  InetAddressIPv6
                   ACCESS  read-write
                   STATUS  mandatory
                   DESCRIPTION
                           "Config source ipv6 address."
                   ::= { onuDMcstConfigProfileEntry 9 }

               onuDMcstIpv6AddressRangeStart OBJECT-TYPE
                   SYNTAX  InetAddressIPv6
                   ACCESS  read-write
                   STATUS  mandatory
                   DESCRIPTION
                           "Config start destination ipv6 address."
                   ::= { onuDMcstConfigProfileEntry 10 }

               onuDMcstIpv6AddressRangeStop OBJECT-TYPE
                   SYNTAX  InetAddressIPv6
                   ACCESS  read-write
                   STATUS  mandatory
                   DESCRIPTION
                           "Config end destination ipv6 address."
                   ::= { onuDMcstConfigProfileEntry 11 }

               onuDMcstImputedGroupBandwidth OBJECT-TYPE
                   SYNTAX  INTEGER
                   UNITS   "kbps"
                   ACCESS  read-write
                   STATUS  mandatory
                   DESCRIPTION
                           "Config imputed group bandwidth.(1-1244160)kbps"
                   ::= { onuDMcstConfigProfileEntry 12 }

               onuDMcstPreviewLength OBJECT-TYPE
                   SYNTAX  INTEGER
                   ACCESS  read-write
                   STATUS  mandatory
                   DESCRIPTION
                           "The maximum duration of each preview in seconds."
                   ::= { onuDMcstConfigProfileEntry 13 }

               onuDMcstPreviewRepeatTime OBJECT-TYPE
                   SYNTAX  INTEGER
                   ACCESS  read-write
                   STATUS  mandatory
                   DESCRIPTION
                           "The minimum time in seconds between two previews of a given multicast group."
                   ::= { onuDMcstConfigProfileEntry 14 }

               onuDMcstPreviewRepeatCount OBJECT-TYPE
                   SYNTAX  INTEGER
                   ACCESS  read-write
                   STATUS  mandatory
                   DESCRIPTION
                           "The maximum number of times a given multicast group may be previewed."
                   ::= { onuDMcstConfigProfileEntry 15 }

               onuDMcstPreviewResetTime OBJECT-TYPE
                   SYNTAX  INTEGER
                   ACCESS  read-write
                   STATUS  mandatory
                   DESCRIPTION
                           "The time at which the ONU resets the preview repeat counter(24-hour system)."
                   ::= { onuDMcstConfigProfileEntry 16 }

               onuDMcstProfileRowStatus OBJECT-TYPE
                   SYNTAX  RowStatus
                   ACCESS  read-create
                   STATUS  mandatory
                   DESCRIPTION
                           "onu SMcst Profile Row Status."
                   ::= { onuDMcstConfigProfileEntry 17 }


-- Catv配置Profile表

               onuCatvProfileTable OBJECT-TYPE
                   SYNTAX  SEQUENCE OF OnuCatvProfileEntry
                   ACCESS  not-accessible
                   STATUS  mandatory
                   DESCRIPTION
                            "A list of  catv port profile table entries."
                   ::= { nmsGponProfile 12 }

               onuCatvProfileEntry OBJECT-TYPE
                   SYNTAX  OnuCatvProfileEntry
                   ACCESS  not-accessible
                   STATUS  mandatory
                   DESCRIPTION
                            "A collection of additional objects in the
                            ONU catv port profile table."
                   INDEX { onuCatvProfileIndex}
               ::= { onuCatvProfileTable 1}

               OnuCatvProfileEntry ::=
                   SEQUENCE {
                       onuCatvProfileIndex
                           INTEGER,
                       onuCatvProfileName
                           OCTET STRING,
               onuCatvGainType
                   INTEGER,
               onuCatvAgcUpValue
                   INTEGER,
               onuCatvAgcRange
                   INTEGER,
               onuCatvMgcTxAttenuation
                   INTEGER,
               onuCatvAlarmInputLowThreshold
                   INTEGER,
               onuCatvAlarmInputLowClearThreshold
                   INTEGER,
               onuCatvAlarmInputHighThreshold
                   INTEGER,
               onuCatvAlarmInputHighClearThreshold
                   INTEGER,
               onuCatvAlarmOutputLowThreshold
                   INTEGER,
               onuCatvAlarmOutputLowClearThreshold
                   INTEGER,
               onuCatvAlarmOutputHighThreshold
                   INTEGER,
               onuCatvAlarmOutputHighClearThreshold
                   INTEGER,
               onuCatvAlarmVoltageLowThreshold
                   INTEGER, 
               onuCatvAlarmVoltageLowClearThreshold
                   INTEGER,
               onuCatvAlarmVoltageHighThreshold
                   INTEGER,
               onuCatvAlarmVoltageHighClearThreshold
                   INTEGER,
               onuCatvAlarmTemperatureLowThreshold
                   INTEGER,
               onuCatvAlarmTemperatureLowClearThreshold
                   INTEGER,   
               onuCatvAlarmTemperatureHighThreshold
                   INTEGER,
               onuCatvAlarmTemperatureHighClearThreshold
                   INTEGER,
               onuCatvProfileRowStatus
                   RowStatus
               }


               onuCatvProfileIndex OBJECT-TYPE
                   SYNTAX  INTEGER
                   ACCESS  read-only
                   STATUS  mandatory
                   DESCRIPTION
                           "profile index ."
                   ::= { onuCatvProfileEntry 1 }
                   
               onuCatvProfileName OBJECT-TYPE
                   SYNTAX  OCTET STRING
                   ACCESS  read-write
                   STATUS  mandatory
                   DESCRIPTION
                           "The name of a profile. "
                   ::= { onuCatvProfileEntry 2 }

               onuCatvGainType OBJECT-TYPE
                   SYNTAX  INTEGER{
                            agc(1),
                            mgc(2)
                            }
                   ACCESS  read-write
                   STATUS  mandatory
                   DESCRIPTION
                           "Config Catv gain type:
                            1 -- agc
                            2 -- mgc"
                   ::= { onuCatvProfileEntry 3 }  
                   
               onuCatvAgcUpValue OBJECT-TYPE
                   SYNTAX  INTEGER(-80..0)
                   ACCESS  read-write
                   STATUS  mandatory
                   DESCRIPTION
                           "Config agc power up value.(-80-0, 0.1dBm)"
                   ::= { onuCatvProfileEntry 4 }

               onuCatvAgcRange OBJECT-TYPE
                   SYNTAX  INTEGER(0..100)
                   ACCESS  read-write
                   STATUS  mandatory
                   DESCRIPTION
                           "Config agc power range.(0-100, 0.1dBm)"
                   ::= { onuCatvProfileEntry 5 }

               onuCatvMgcTxAttenuation OBJECT-TYPE
                   SYNTAX  INTEGER(0..150)
                   ACCESS  read-write
                   STATUS  mandatory
                   DESCRIPTION
                           "Config mac tx attenuation.(0-150,0.1dBm)"
                   ::= { onuCatvProfileEntry 6 }

               onuCatvAlarmInputLowThreshold OBJECT-TYPE
                   SYNTAX  INTEGER
                   ACCESS  read-write
                   STATUS  mandatory
                   DESCRIPTION
                           "Config catv input alarm low threshold."
                   ::= { onuCatvProfileEntry 7 }

               onuCatvAlarmInputLowClearThreshold OBJECT-TYPE
                   SYNTAX  INTEGER
                   ACCESS  read-write
                   STATUS  mandatory
                   DESCRIPTION
                           "Config catv input alarm low clear threshold"
                   ::= { onuCatvProfileEntry 8 }

               onuCatvAlarmInputHighThreshold OBJECT-TYPE
                   SYNTAX  INTEGER
                   ACCESS  read-write
                   STATUS  mandatory
                   DESCRIPTION
                           "Config catv input alarm high threshold."
                   ::= { onuCatvProfileEntry 9 }

               onuCatvAlarmInputHighClearThreshold OBJECT-TYPE
                   SYNTAX  INTEGER
                   ACCESS  read-write
                   STATUS  mandatory
                   DESCRIPTION
                           "Config catv input alarm high clear threshold."
                   ::= { onuCatvProfileEntry 10 }

               onuCatvAlarmOutputLowThreshold OBJECT-TYPE
                   SYNTAX  INTEGER
                   ACCESS  read-write
                   STATUS  mandatory
                   DESCRIPTION
                           "Config catv output alarm low threshold."
                   ::= { onuCatvProfileEntry 11 }

               onuCatvAlarmOutputLowClearThreshold OBJECT-TYPE
                   SYNTAX  INTEGER
                   ACCESS  read-write
                   STATUS  mandatory
                   DESCRIPTION
                           "Config catv output alarm low clear threshold."
                   ::= { onuCatvProfileEntry 12 }

               onuCatvAlarmOutputHighThreshold OBJECT-TYPE
                   SYNTAX  INTEGER
                   ACCESS  read-write
                   STATUS  mandatory
                   DESCRIPTION
                           "Config catv output alarm high threshold."
                   ::= { onuCatvProfileEntry 13 }

               onuCatvAlarmOutputHighClearThreshold OBJECT-TYPE
                   SYNTAX  INTEGER
                   ACCESS  read-write
                   STATUS  mandatory
                   DESCRIPTION
                           "Config catv output alarm high clear threshold."
                   ::= { onuCatvProfileEntry 14 }

               onuCatvAlarmVoltageLowThreshold OBJECT-TYPE
                   SYNTAX  INTEGER
                   ACCESS  read-write
                   STATUS  mandatory
                   DESCRIPTION
                           "Config catv voltage alarm low threshold."
                   ::= { onuCatvProfileEntry 15 }

               onuCatvAlarmVoltageLowClearThreshold OBJECT-TYPE
                   SYNTAX  INTEGER
                   ACCESS  read-write
                   STATUS  mandatory
                   DESCRIPTION
                           "Config catv voltage alarm low clear threshold."
                   ::= { onuCatvProfileEntry 16 }
               
               onuCatvAlarmVoltageHighThreshold OBJECT-TYPE
                   SYNTAX  INTEGER
                   ACCESS  read-write
                   STATUS  mandatory
                   DESCRIPTION
                           "Config catv voltage alarm high threshold."
                   ::= { onuCatvProfileEntry 17 }

               onuCatvAlarmVoltageHighClearThreshold OBJECT-TYPE
                   SYNTAX  INTEGER
                   ACCESS  read-write
                   STATUS  mandatory
                   DESCRIPTION
                           "Config catv voltage alarm high clear threshold."
                   ::= { onuCatvProfileEntry 18 }

               onuCatvAlarmTemperatureLowThreshold OBJECT-TYPE
                   SYNTAX  INTEGER
                   ACCESS  read-write
                   STATUS  mandatory
                   DESCRIPTION
                           "Config catv temperature alarm low threshold."
                   ::= { onuCatvProfileEntry 19 }

               onuCatvAlarmTemperatureLowClearThreshold OBJECT-TYPE
                   SYNTAX  INTEGER
                   ACCESS  read-write
                   STATUS  mandatory
                   DESCRIPTION
                           "Config catv temperature alarm low clear threshold."
                   ::= { onuCatvProfileEntry 20 }

               onuCatvAlarmTemperatureHighThreshold OBJECT-TYPE
                   SYNTAX  INTEGER
                   ACCESS  read-write
                   STATUS  mandatory
                   DESCRIPTION
                           "Config catv temperature alarm high threshold."
                   ::= { onuCatvProfileEntry 21 }

               onuCatvAlarmTemperatureHighClearThreshold OBJECT-TYPE
                   SYNTAX  INTEGER
                   ACCESS  read-write
                   STATUS  mandatory
                   DESCRIPTION
                           "Config catv temperature alarm high clear threshold."
                   ::= { onuCatvProfileEntry 22 }

               onuCatvProfileRowStatus OBJECT-TYPE
                   SYNTAX  RowStatus
                   ACCESS  read-create
                   STATUS  mandatory
                   DESCRIPTION
                           "onu Catv Profile Row Status."
                   ::= { onuCatvProfileEntry 23 } 
    
-- VOIP端口配置Profile表  

             onuVoipConfigProfileTable OBJECT-TYPE
                 SYNTAX  SEQUENCE OF OnuVoipConfigProfileEntry
                 ACCESS  not-accessible
                 STATUS  mandatory
                 DESCRIPTION
                          "Onu Voip configuration profile table."
                 ::= { nmsGponProfile 13 }

             onuVoipConfigProfileEntry OBJECT-TYPE
                 SYNTAX OnuVoipConfigProfileEntry
                 ACCESS  not-accessible
                 STATUS  mandatory
                 DESCRIPTION
                          "Onu Voip configuration profile entry."
                 INDEX { onuVoipPortProfileIndex }
             ::= { onuVoipConfigProfileTable 1 }

             OnuVoipConfigProfileEntry ::=
                 SEQUENCE {
                    onuVoipConfigProfileIndex
                        INTEGER,
                    onuVoipConfigProfileName
                        OCTET STRING,
                    onuVoipConfigProfileVoipType
                        INTEGER,
                    onuVoipConfigProfileH248Primarymgc
                        OCTET STRING,
                    onuVoipConfigProfileH248Secondarymgc
                        OCTET STRING,
                    onuVoipConfigProfileH248Version
                        INTEGER,
                    onuVoipConfigProfileH248MessageFormat
                        INTEGER,
                    onuVoipConfigProfileH248MaxRetryTime
                        INTEGER,
                    onuVoipConfigProfileH248MaxRetryCount
                        INTEGER,
                    onuVoipConfigProfileSipProxyServer
                        OCTET STRING,
                    onuVoipConfigProfileSipOutboundProxy
                        OCTET STRING,
                    onuVoipConfigProfileSipRegistrarServer
                        OCTET STRING,
                    onuVoipConfigProfileSipPrimaryDns
                        INTEGER,
                    onuVoipConfigProfileSipSecondaryDns
                        INTEGER,
                    onuVoipConfigProfileSipRegExpTime
                        INTEGER,
                    onuVoipConfigProfileSipReregistrationTime
                        INTEGER,
                    onuVoipConfigProfileBindIpHostPortId
                        INTEGER,
                    onuVoipConfigProfileBindUdpPort
                        INTEGER,
                    onuVoipConfigProfileSoftswitchVendor
                        OCTET STRING,
                    onuVoipConfigProfileMediaFaxMode
                        INTEGER,
                    onuVoipConfigProfileMediaCodec
                        INTEGER,
                    onuVoipConfigProfileMediaPaketPeriod
                        INTEGER,
                    onuVoipConfigProfileRtpPortStart
                        INTEGER,
                    onuVoipConfigProfileRtpPortEnd
                        INTEGER,
                    onuVoipConfigProfileRtpDscp
                        INTEGER,
                    onuVoipConfigProfileRowStatus
                        RowStatus,
                    onuVoipConfigProfileSipHostPartUri
                        OCTET STRING,
                    onuVoipConfigProfileVoiceSvcJitterTarget
                        INTEGER,
                    onuVoipConfigProfileVoiceSvcJitterBuffMax
                        INTEGER,
                    onuVoipConfigProfileVoiceSvcEchoCancelInd
                        INTEGER,
                    onuVoipConfigProfileVoiceSvcHookFlashMinTime
                        INTEGER,
                    onuVoipConfigProfileVoiceSvcHookFlashMaxTime
                        INTEGER
                }

          onuVoipConfigProfileIndex OBJECT-TYPE
              SYNTAX  INTEGER
              ACCESS  read-only
              STATUS  mandatory
              DESCRIPTION
                      "Index of the table, ONU voip configuration profile INDEX 1."
              ::= { onuVoipConfigProfileEntry 1 }
                 
          onuVoipConfigProfileName OBJECT-TYPE
              SYNTAX  OCTET STRING
              ACCESS  read-write
              STATUS  mandatory
              DESCRIPTION
                      "ONU Voip configuration profile name."
              ::= { onuVoipConfigProfileEntry 2 }
                 
          onuVoipConfigProfileVoipType OBJECT-TYPE
              SYNTAX  INTEGER{
                        sip(1),
                        h248(2)
                        }
              ACCESS  read-write
              STATUS  mandatory
              DESCRIPTION
                      "VoipType: 1 sip, 2 h248. Default value is 1. "
              ::= { onuVoipConfigProfileEntry 3 }
                 
          onuVoipConfigProfileH248Primarymgc OBJECT-TYPE
              SYNTAX  OCTET STRING
              ACCESS  read-write
              STATUS  mandatory

              DESCRIPTION
                      "H248 Primary mgc."
              ::= { onuVoipConfigProfileEntry 4 }

          onuVoipConfigProfileH248Secondarymgc OBJECT-TYPE
              SYNTAX  OCTET STRING
              ACCESS  read-write
              STATUS  mandatory

              DESCRIPTION
                      "H248 Secondary mgc."
              ::= { onuVoipConfigProfileEntry 5 }
                    
          onuVoipConfigProfileH248Version OBJECT-TYPE
              SYNTAX  INTEGER{
                        version1(1),
                        version2(2),
                        version3(3),
                        version4(4)
                        }
              ACCESS  read-write
              STATUS  mandatory
              DESCRIPTION
                      "H248 Version: 1 version1, 2 version2, 3 version3, 4 version4. Default value is 1. "
              ::= { onuVoipConfigProfileEntry 6 }

          onuVoipConfigProfileH248MessageFormat OBJECT-TYPE
              SYNTAX  INTEGER{
                        text_long(0),
                        text_short(1),
                        binary(2)
                        }
              ACCESS  read-write
              STATUS  mandatory
              DESCRIPTION
                       "H248 Message Format:0 text_long,1 text_short,2 binary."
              ::= { onuVoipConfigProfileEntry 7 }

          onuVoipConfigProfileH248MaxRetryTime OBJECT-TYPE          
              SYNTAX  INTEGER
              ACCESS  read-write
              STATUS  mandatory
              DESCRIPTION
                      "max retry time."
              ::= { onuVoipConfigProfileEntry 8 }

          onuVoipConfigProfileH248MaxRetryCount OBJECT-TYPE          
              SYNTAX  INTEGER
              ACCESS  read-write
              STATUS  mandatory
              DESCRIPTION
                      "max retry count."
              ::= { onuVoipConfigProfileEntry 9 }

          onuVoipConfigProfileSipProxyServer OBJECT-TYPE
              SYNTAX  OCTET STRING
              ACCESS  read-write
              STATUS  mandatory

              DESCRIPTION
                      "sip proxy server."
              ::= { onuVoipConfigProfileEntry 10 }

          onuVoipConfigProfileSipOutboundProxy OBJECT-TYPE
              SYNTAX  OCTET STRING
              ACCESS  read-write
              STATUS  mandatory

              DESCRIPTION
                      "sip outbound proxy server."
              ::= { onuVoipConfigProfileEntry 11 }

          onuVoipConfigProfileSipRegistrarServer OBJECT-TYPE
              SYNTAX  OCTET STRING
              ACCESS  read-write
              STATUS  mandatory

              DESCRIPTION
                      "sip registrar server."
              ::= { onuVoipConfigProfileEntry 12 }

          onuVoipConfigProfileSipPrimaryDns OBJECT-TYPE
              SYNTAX  INTEGER
              ACCESS  read-write
              STATUS  mandatory
              DESCRIPTION
                      "sip primary dns."
              ::= { onuVoipConfigProfileEntry 13 }

          onuVoipConfigProfileSipSecondaryDns OBJECT-TYPE
              SYNTAX  INTEGER
              ACCESS  read-write
              STATUS  mandatory
              DESCRIPTION
                      "sip secondary dns."
              ::= { onuVoipConfigProfileEntry 14 }

          onuVoipConfigProfileSipRegExpTime OBJECT-TYPE
              SYNTAX  INTEGER
              ACCESS  read-write
              STATUS  mandatory
              DESCRIPTION
                      "sip reg exp time."
              ::= { onuVoipConfigProfileEntry 15 }

          onuVoipConfigProfileSipReregistrationTime OBJECT-TYPE
              SYNTAX  INTEGER
              ACCESS  read-write
              STATUS  mandatory
              DESCRIPTION
                      "sip reregistration time."
              ::= { onuVoipConfigProfileEntry 16 }

          onuVoipConfigProfileBindIpHostPortId OBJECT-TYPE
              SYNTAX  INTEGER
              ACCESS  read-write
              STATUS  mandatory
              DESCRIPTION
                      "bind ip host port id."
              ::= { onuVoipConfigProfileEntry 17 }

          onuVoipConfigProfileBindUdpPort OBJECT-TYPE
              SYNTAX  INTEGER
              ACCESS  read-write
              STATUS  mandatory
              DESCRIPTION
                      "bind udp port."
              ::= { onuVoipConfigProfileEntry 18 }

          onuVoipConfigProfileSoftswitchVendor OBJECT-TYPE
              SYNTAX  OCTET STRING
              ACCESS  read-write
              STATUS  mandatory

              DESCRIPTION
                      "softswitch vendor."
              ::= { onuVoipConfigProfileEntry 19 }
              
          onuVoipConfigProfileMediaFaxMode OBJECT-TYPE
              SYNTAX  INTEGER{
                        passthru(0),
                        t38(1)
                        }
              ACCESS  read-write
              STATUS  mandatory
              DESCRIPTION
                      "media fax mode:0 passthru 1 t38."
              ::= { onuVoipConfigProfileEntry 20 }

          onuVoipConfigProfileMediaCodec OBJECT-TYPE
              SYNTAX  INTEGER
              ACCESS  read-write
              STATUS  mandatory
              DESCRIPTION
                      "media codec."
              ::= { onuVoipConfigProfileEntry 21 }

          onuVoipConfigProfileMediaPaketPeriod OBJECT-TYPE
              SYNTAX  INTEGER
              ACCESS  read-write
              STATUS  mandatory
              DESCRIPTION
                      "media paket period."
              ::= { onuVoipConfigProfileEntry 22 }

          onuVoipConfigProfileRtpPortStart OBJECT-TYPE
              SYNTAX  INTEGER
              ACCESS  read-write
              STATUS  mandatory
              DESCRIPTION
                      "rtp port start."
              ::= { onuVoipConfigProfileEntry 23 }

          onuVoipConfigProfileRtpPortEnd OBJECT-TYPE           
              SYNTAX  INTEGER
              ACCESS  read-write
              STATUS  mandatory
              DESCRIPTION
                      "rtp port end."
              ::= { onuVoipConfigProfileEntry 24 }

          onuVoipConfigProfileRtpDscp OBJECT-TYPE
              SYNTAX  INTEGER
              ACCESS  read-write
              STATUS  mandatory
              DESCRIPTION
                      "rtp dscp."
              ::= { onuVoipConfigProfileEntry 25 }

          onuVoipConfigProfileRowStatus OBJECT-TYPE
              SYNTAX  RowStatus
              ACCESS  read-create
              STATUS  mandatory
              DESCRIPTION
                      ""
              ::= { onuVoipConfigProfileEntry 26 }  
              
          onuVoipConfigProfileSipHostPartUri OBJECT-TYPE
              SYNTAX  OCTET STRING
              ACCESS  read-write
              STATUS  mandatory
              DESCRIPTION
                      "sip host part URI."
              ::= { onuVoipConfigProfileEntry 27 }
              
          onuVoipConfigProfileVoiceSvcJitterTarget OBJECT-TYPE
              SYNTAX  INTEGER
              ACCESS  read-write
              STATUS  mandatory
              DESCRIPTION
                      "voice service jitter target (1-3000 ms)."
              ::= { onuVoipConfigProfileEntry 28 }
              
          onuVoipConfigProfileVoiceSvcJitterBuffMax OBJECT-TYPE
              SYNTAX  INTEGER
              ACCESS  read-write
              STATUS  mandatory
              DESCRIPTION
                      "maximum depth of voice service jitter buffer (1-3000 ms)."
              ::= { onuVoipConfigProfileEntry 29 }
                      
          onuVoipConfigProfileVoiceSvcEchoCancelInd OBJECT-TYPE
              SYNTAX  INTEGER{
                        off(0),
                        on(1)
                      }
              ACCESS  read-write
              STATUS  mandatory
              DESCRIPTION
                      "voice service echo cancel ind."
              ::= { onuVoipConfigProfileEntry 30 }
              
          onuVoipConfigProfileVoiceSvcHookFlashMinTime OBJECT-TYPE
              SYNTAX  INTEGER
              ACCESS  read-write
              STATUS  mandatory
              DESCRIPTION
                      "voice service hook flash minimum time (1-3000 ms)."
              ::= { onuVoipConfigProfileEntry 31 }
              
          onuVoipConfigProfileVoiceSvcHookFlashMaxTime OBJECT-TYPE
              SYNTAX  INTEGER
              ACCESS  read-write
              STATUS  mandatory
              DESCRIPTION
                      "voice service hook flash maximum time (1-3000 ms)."
              ::= { onuVoipConfigProfileEntry 32 }
              

-- ONU sip拨号方案配置Profile表

             onuSipDialPlanConfigProfileTable OBJECT-TYPE
                 SYNTAX  SEQUENCE OF OnuSipDialPlanConfigProfileEntry
                 ACCESS  not-accessible
                 STATUS  mandatory
                 DESCRIPTION
                          "Onu sip dial plan config profile table."
                 ::= { nmsGponProfile 14 }

             onuSipDialPlanConfigProfileEntry OBJECT-TYPE
                 SYNTAX OnuSipDialPlanConfigProfileEntry
                 ACCESS  not-accessible
                 STATUS  mandatory
                 DESCRIPTION
                          "Onu sip dial plan config profile entry."
                 INDEX { onuSipDialPlanConfigProfileIndex1,onuSipDialPlanConfigProfileIndex2 }
             ::= { onuSipDialPlanConfigProfileTable 1 }

             OnuSipDialPlanConfigProfileEntry ::=
                 SEQUENCE {
                     onuSipDialPlanConfigProfileIndex1
                         INTEGER,
                     onuSipDialPlanConfigProfileIndex2
                         INTEGER,
                     onuSipDialPlanConfigProfileName 
                         OCTET STRING,
                     onuSipDialPlanConfigSipDialPlanToken
                         OCTET STRING,
                     onuSipDialPlanConfigProfileRowStatus
                         RowStatus                      
                 }

          onuSipDialPlanConfigProfileIndex1 OBJECT-TYPE
              SYNTAX  INTEGER
              ACCESS  read-only
              STATUS  mandatory
              DESCRIPTION
                      "Index of the table, ONU sip dial plan config profile index 1."
              ::= { onuSipDialPlanConfigProfileEntry 1 }
                 
          onuSipDialPlanConfigProfileIndex2 OBJECT-TYPE
              SYNTAX  INTEGER
              ACCESS  read-only
              STATUS  mandatory
              DESCRIPTION
                      "Index of the table, ONU sip dial plan config profile index 2."
              ::= { onuSipDialPlanConfigProfileEntry 2 }
                 
          onuSipDialPlanConfigProfileName OBJECT-TYPE
              SYNTAX  OCTET STRING
              ACCESS  read-write
              STATUS  mandatory
              DESCRIPTION
                      "ONU sip dial plan config profile name."
              ::= { onuSipDialPlanConfigProfileEntry 3 }
                 
          onuSipDialPlanConfigSipDialPlanToken OBJECT-TYPE
              SYNTAX  OCTET STRING
              ACCESS  read-write
              STATUS  mandatory
              DESCRIPTION
                      "ONU sip dial plan config profile token."
              ::= { onuSipDialPlanConfigProfileEntry 4 }

          onuSipDialPlanConfigProfileRowStatus OBJECT-TYPE
              SYNTAX  RowStatus
              ACCESS  read-create
              STATUS  mandatory

              DESCRIPTION
                      ""
              ::= { onuSipDialPlanConfigProfileEntry 5 }
              
-- ONU VEIP配置Profile表

             onuVEIPConfigProfileTable OBJECT-TYPE
                 SYNTAX  SEQUENCE OF OnuVEIPConfigProfileEntry
                 ACCESS  not-accessible
                 STATUS  mandatory
                 DESCRIPTION
                          "Onu VEIP config profile table."
                 ::= { nmsGponProfile 15 }

             onuVEIPConfigProfileEntry OBJECT-TYPE
                 SYNTAX OnuVEIPConfigProfileEntry
                 ACCESS  not-accessible
                 STATUS  mandatory
                 DESCRIPTION
                          "Onu VEIP config profile entry."
                 INDEX { onuVEIPConfigProfileIndex1 }
             ::= { onuVEIPConfigProfileTable 1 }

             OnuVEIPConfigProfileEntry ::=
                 SEQUENCE {
                     onuVEIPConfigProfileIndex
                         INTEGER,
                     onuVEIPConfigProfileName
                         OCTET STRING,
                     onuVEIPConfigProfileMgmtBindIpHostPort 
                         INTEGER,
                     onuVEIPConfigProfileTr069Url
                         OCTET STRING,    
                     onuVEIPConfigProfileTr069Username
                         OCTET STRING,
                     onuVEIPConfigProfileTr069Password
                         OCTET STRING,
                     onuVEIPConfigProfileRowStatus
                         RowStatus,
                     onuVEIPConfigProfileTr069Tci
                         INTEGER
                 }

          onuVEIPConfigProfileIndex OBJECT-TYPE
              SYNTAX  INTEGER
              ACCESS  read-only
              STATUS  mandatory
              DESCRIPTION
                      "Index of the table, ONU VEIP config profile index."
              ::= { onuVEIPConfigProfileEntry 1 }
                 
          onuVEIPConfigProfileName OBJECT-TYPE
              SYNTAX  OCTET STRING
              ACCESS  read-only
              STATUS  mandatory
              DESCRIPTION
                      "ONU VEIP config profile name."
              ::= { onuVEIPConfigProfileEntry 2 }
                 
          onuVEIPConfigProfileMgmtBindIpHostPort OBJECT-TYPE
              SYNTAX  INTEGER (0..8)
              ACCESS  read-write
              STATUS  mandatory
              DESCRIPTION
                      "ONU VEIP config bind ip-host port."
              ::= { onuVEIPConfigProfileEntry 3 }
                 
          onuVEIPConfigProfileTr069Url OBJECT-TYPE
              SYNTAX  OCTET STRING (SIZE (1..128))
              ACCESS  read-write
              STATUS  mandatory
              DESCRIPTION
                      "ONU VEIP config Tr-069 Url."
              ::= { onuVEIPConfigProfileEntry 4 }  
              
          onuVEIPConfigProfileTr069Username OBJECT-TYPE
              SYNTAX  OCTET STRING (SIZE (1..25))
              ACCESS  read-write
              STATUS  mandatory
              DESCRIPTION
                      "ONU VEIP config Tr-069 Username."
              ::= { onuVEIPConfigProfileEntry 5 }
          
          onuVEIPConfigProfileTr069Password OBJECT-TYPE
              SYNTAX  OCTET STRING (SIZE (1..25))
              ACCESS  read-write
              STATUS  mandatory
              DESCRIPTION
                      "ONU VEIP config Tr-069 password."
              ::= { onuVEIPConfigProfileEntry 6 }

          onuVEIPConfigProfileRowStatus OBJECT-TYPE
              SYNTAX  RowStatus
              ACCESS  read-create
              STATUS  mandatory

              DESCRIPTION
                      ""
              ::= { onuVEIPConfigProfileEntry 7 }

          onuVEIPConfigProfileTr069Tci OBJECT-TYPE
              SYNTAX  INTEGER
              ACCESS  read-write
              STATUS  mandatory
              DESCRIPTION
                      "ONU VEIP config Tr-069 associtated tag.
                      Format 16 bit, MSB 3 is priority, LSB 12 is vlanId"
              ::= { onuVEIPConfigProfileEntry 8 }  

-- ONU storm control table

    onuStormCtrlProfileTable OBJECT-TYPE
        SYNTAX  SEQUENCE OF OnuStormCtrlProfileEntry
        ACCESS  not-accessible
        STATUS  mandatory
        DESCRIPTION
            "ONU storm control profile table."
        ::= { nmsGponProfile 16 }
        
    onuStormCtrlProfileEntry OBJECT-TYPE
        SYNTAX  OnuStormCtrlProfileEntry
        ACCESS  not-accessible
        STATUS  mandatory
        DESCRIPTION
            "A collection of additional objects in the
            ONU storm control profile table."
        INDEX { onuStormCtrlProfileIndex }
        ::= { onuStormCtrlProfileTable 1 }
        
    OnuStormCtrlProfileEntry ::=
        SEQUENCE {
            onuStormCtrlProfileIndex
                INTEGER,
            onuStormCtrlProfileName
                DisplayString,
            onuStormCtrlProfileUsBcLimit
                INTEGER,
            onuStormCtrlProfileUsMcLimit
                INTEGER,
            onuStormCtrlProfileUsFldUcLimit
                INTEGER,
            onuStormCtrlProfileRowStatus
                RowStatus
        }

    onuStormCtrlProfileIndex  OBJECT-TYPE
        SYNTAX  INTEGER
        ACCESS  read-only
        STATUS  mandatory
        DESCRIPTION
            "Index of storm control profile."
        ::= { onuStormCtrlProfileEntry 1 }

    onuStormCtrlProfileName  OBJECT-TYPE
        SYNTAX  DisplayString
        ACCESS  read-write
        STATUS  mandatory
        DESCRIPTION
            "Name of storm control profile."
        ::= { onuStormCtrlProfileEntry 2 }

    onuStormCtrlProfileUsBcLimit  OBJECT-TYPE
        SYNTAX  INTEGER
        ACCESS  read-write
        STATUS  mandatory
        DESCRIPTION
            "ID of the rate limit profile used to limit upstream broadcast traffic."
        ::= { onuStormCtrlProfileEntry 3 }

    onuStormCtrlProfileUsMcLimit  OBJECT-TYPE
        SYNTAX  INTEGER
        ACCESS  read-write
        STATUS  mandatory
        DESCRIPTION
            "ID of the rate limit profile used to limit upstream multicast traffic."
        ::= { onuStormCtrlProfileEntry 4 }

    onuStormCtrlProfileUsFldUcLimit  OBJECT-TYPE
        SYNTAX  INTEGER
        ACCESS  read-write
        STATUS  mandatory
        DESCRIPTION
            "ID of the rate limit profile used to limit upstream flooded unicast traffic."
        ::= { onuStormCtrlProfileEntry 5 }

    onuStormCtrlProfileRowStatus  OBJECT-TYPE
        SYNTAX  RowStatus
        ACCESS  read-write
        STATUS  mandatory
        DESCRIPTION
            ""
        ::= { onuStormCtrlProfileEntry 6 }

-- ONU loopback detection table

    onuLoopbackDetectionProfileTable OBJECT-TYPE
        SYNTAX  SEQUENCE OF OnuLoopbackDetectionProfileEntry
        ACCESS  not-accessible
        STATUS  mandatory
        DESCRIPTION
            "ONU loopback detection profile table."
        ::= { nmsGponProfile 17 }

    onuLoopbackDetectionProfileEntry OBJECT-TYPE
        SYNTAX  OnuLoopbackDetectionProfileEntry
        ACCESS  not-accessible
        STATUS  mandatory
        DESCRIPTION
            "A collection of additional objects in the
            ONU loopback detection profile table."
        INDEX { onuLoopbackDetectionProfileIndex }
        ::= { onuLoopbackDetectionProfileTable 1 }

    OnuLoopbackDetectionProfileEntry ::=
        SEQUENCE {
            onuLoopbackDetectionProfileIndex
                INTEGER,
            onuLoopbackDetectionProfileName
                DisplayString,
            onuLoopbackDetectionProfileAdmin
                INTEGER,
            onuLoopbackDetectionProfileAutoShut
                INTEGER,
            onuLoopbackDetectionProfileMsgFrequency
                INTEGER,
            onuLoopbackDetectionProfileRecoveryInterval
                INTEGER,
            onuLoopbackDetectionProfilePortVlanList
                OCTET STRING,
            onuLoopbackDetectionProfileRowStatus
                RowStatus
        }

    onuLoopbackDetectionProfileIndex  OBJECT-TYPE
        SYNTAX  INTEGER
        ACCESS  read-only
        STATUS  mandatory
        DESCRIPTION
            "Index of loopback detection profile."
        ::= { onuLoopbackDetectionProfileEntry 1 }

    onuLoopbackDetectionProfileName  OBJECT-TYPE
        SYNTAX  DisplayString
        ACCESS  read-write
        STATUS  mandatory
        DESCRIPTION
            "Name of loopback detection profile."
        ::= { onuLoopbackDetectionProfileEntry 2 }

    onuLoopbackDetectionProfileAdmin  OBJECT-TYPE
        SYNTAX  INTEGER {
            disable(0),
            enable(1)
        }
        ACCESS  read-write
        STATUS  mandatory
        DESCRIPTION
            "set uni loopback detection admin-state. 0-disable 1-enable default 1."
        ::= { onuLoopbackDetectionProfileEntry 3 }

    onuLoopbackDetectionProfileAutoShut  OBJECT-TYPE
        SYNTAX  INTEGER {
            disable(0),
            enable(1)
        }
        ACCESS  read-write
        STATUS  mandatory
        DESCRIPTION
            "loopback detection uni port auto shutdown. 0-disable 1-enable default 1."
        ::= { onuLoopbackDetectionProfileEntry 4 }

    onuLoopbackDetectionProfileMsgFrequency  OBJECT-TYPE
        SYNTAX  INTEGER
        ACCESS  read-write
        STATUS  mandatory
        DESCRIPTION
            "loopback detection message frequency."
        ::= { onuLoopbackDetectionProfileEntry 5 }

    onuLoopbackDetectionProfileRecoveryInterval  OBJECT-TYPE
        SYNTAX  INTEGER
        ACCESS  read-write
        STATUS  mandatory
        DESCRIPTION
            "onu loopback detection loop recovery interval."
        ::= { onuLoopbackDetectionProfileEntry 6 }

    onuLoopbackDetectionProfilePortVlanList  OBJECT-TYPE
        SYNTAX  OCTET STRING
        ACCESS  read-write
        STATUS  mandatory
        DESCRIPTION
            "onu port loopback detection packet Port-Vlan table. Entries is separated by comma, and with format pUNIcCVLANsSVLAN.
            Example: 'p1c100s50,p1c2501s0,p2c0s0' means loopback detection on UNI 1 CVLAN 100 SVLAN 50, and UNI 1 CVLAN 2501 no SVLAN, and UNI 2 no CVLAN no SVLAN."
        ::= { onuLoopbackDetectionProfileEntry 7 }

    onuLoopbackDetectionProfileRowStatus  OBJECT-TYPE
        SYNTAX  RowStatus
        ACCESS  read-write
        STATUS  mandatory
        DESCRIPTION
            ""
        ::= { onuLoopbackDetectionProfileEntry 8 }

-- ONU SNMP table

    onuSnmpProfileTable OBJECT-TYPE
        SYNTAX  SEQUENCE OF OnuSnmpProfileEntry
        ACCESS  not-accessible
        STATUS  mandatory
        DESCRIPTION
            "ONU SNMP profile table."
        ::= { nmsGponProfile 18 }

    onuSnmpProfileEntry OBJECT-TYPE
        SYNTAX  OnuSnmpProfileEntry
        ACCESS  not-accessible
        STATUS  mandatory
        DESCRIPTION
            "A collection of objects in the ONU SNMP profile table."
        INDEX { onuSnmpProfileIndex }
        ::= { onuSnmpProfileTable 1 }

    OnuSnmpProfileEntry ::=
        SEQUENCE {
            onuSnmpProfileIndex
                INTEGER,
            onuSnmpProfileName
                DisplayString,
            onuSnmpProfileBindIpHostPort
                INTEGER,
            onuSnmpProfileSnmpVersion
                INTEGER,
            onuSnmpProfileSnmpTrapHost
                IpAddress,
            onuSnmpProfileSnmpTrapHostPort
                INTEGER,
            onuSnmpProfileSnmpSecurityName
                OCTET STRING,
            onuSnmpProfileSnmpCommunityRead
                OCTET STRING,
            onuSnmpProfileSnmpCommunityWrite
                OCTET STRING,
            onuSnmpProfileRowStatus
                RowStatus
        }

    onuSnmpProfileIndex  OBJECT-TYPE
        SYNTAX  INTEGER
        ACCESS  read-only
        STATUS  mandatory
        DESCRIPTION
            "Index of SNMP profile."
        ::= { onuSnmpProfileEntry 1 }

    onuSnmpProfileName  OBJECT-TYPE
        SYNTAX  DisplayString
        ACCESS  read-write
        STATUS  mandatory
        DESCRIPTION
            "Name of SNMP profile."
        ::= { onuSnmpProfileEntry 2 }

    onuSnmpProfileBindIpHostPort OBJECT-TYPE
        SYNTAX  INTEGER
        ACCESS  read-write
        STATUS  mandatory
        DESCRIPTION
            "Bind SNMP config to IP host port ID."
        ::= { onuSnmpProfileEntry 3 }

    onuSnmpProfileSnmpVersion OBJECT-TYPE
        SYNTAX  INTEGER(1..3)
        ACCESS  read-write
        STATUS  mandatory
        DESCRIPTION
            "SNMP protocol version."
        ::= { onuSnmpProfileEntry 4 }

    onuSnmpProfileSnmpTrapHost OBJECT-TYPE
        SYNTAX  IpAddress
        ACCESS  read-write
        STATUS  mandatory
        DESCRIPTION
            "SNMP Trap host address."
        ::= { onuSnmpProfileEntry 5 }

    onuSnmpProfileSnmpTrapHostPort OBJECT-TYPE
        SYNTAX  INTEGER(1..65535)
        ACCESS  read-write
        STATUS  mandatory
        DESCRIPTION
            "SNMP Trap host UDP port."
        ::= { onuSnmpProfileEntry 6 }

    onuSnmpProfileSnmpSecurityName OBJECT-TYPE
        SYNTAX  OCTET STRING (SIZE (0..32))
        ACCESS  read-write
        STATUS  mandatory
        DESCRIPTION
            "SNMP security name."
        ::= { onuSnmpProfileEntry 7 }

    onuSnmpProfileSnmpCommunityRead OBJECT-TYPE
        SYNTAX  OCTET STRING (SIZE (0..32))
        ACCESS  read-write
        STATUS  mandatory
        DESCRIPTION
            "SNMP community for read."
        ::= { onuSnmpProfileEntry 8 }

    onuSnmpProfileSnmpCommunityWrite OBJECT-TYPE
        SYNTAX  OCTET STRING (SIZE (0..32))
        ACCESS  read-write
        STATUS  mandatory
        DESCRIPTION
            "SNMP community for write."
        ::= { onuSnmpProfileEntry 9 }

    onuSnmpProfileRowStatus  OBJECT-TYPE
        SYNTAX  RowStatus
        ACCESS  read-write
        STATUS  mandatory
        DESCRIPTION
            "Row status of SNMP profile entry."
        ::= { onuSnmpProfileEntry 10 }

-- ONU Voice-VLAN table

    onuVoiceVlanProfile OBJECT IDENTIFIER ::= { nmsGponProfile 19 }

    onuVoiceVlanProfileTable OBJECT-TYPE
        SYNTAX  SEQUENCE OF OnuVoiceVlanProfileEntry
        ACCESS  not-accessible
        STATUS  mandatory
        DESCRIPTION
            "ONU Voice-VLAN profile table."
        ::= { onuVoiceVlanProfile 1 }

    onuVoiceVlanProfileEntry OBJECT-TYPE
        SYNTAX  OnuVoiceVlanProfileEntry
        ACCESS  not-accessible
        STATUS  mandatory
        DESCRIPTION
            "A collection of objects in the ONU Voice-VLAN profile table."
        INDEX { onuVoiceVlanProfileIndex }
        ::= { onuVoiceVlanProfileTable 1 }

    OnuVoiceVlanProfileEntry ::=
        SEQUENCE {
            onuVoiceVlanProfileIndex
                INTEGER,
            onuVoiceVlanProfileName
                DisplayString,
            onuVoiceVlanProfileRowStatus
                RowStatus
        }

    onuVoiceVlanProfileIndex  OBJECT-TYPE
        SYNTAX  INTEGER
        ACCESS  read-only
        STATUS  mandatory
        DESCRIPTION
            "Index of Voice-VLAN profile."
        ::= { onuVoiceVlanProfileEntry 1 }

    onuVoiceVlanProfileName  OBJECT-TYPE
        SYNTAX  DisplayString
        ACCESS  read-create
        STATUS  mandatory
        DESCRIPTION
            "Name of Voice-VLAN profile."
        ::= { onuVoiceVlanProfileEntry 2 }

    onuVoiceVlanProfileRowStatus  OBJECT-TYPE
        SYNTAX  RowStatus
        ACCESS  read-create
        STATUS  mandatory
        DESCRIPTION
            "Row status of Voice-VLAN profile entry."
        ::= { onuVoiceVlanProfileEntry 3 }

    onuVoiceVlanProfileMacTable OBJECT-TYPE
        SYNTAX  SEQUENCE OF OnuVoiceVlanProfileMacEntry
        ACCESS  not-accessible
        STATUS  mandatory
        DESCRIPTION
            "ONU Voice-VLAN profile MAC address table."
        ::= { onuVoiceVlanProfile 2 }

    onuVoiceVlanProfileMacEntry OBJECT-TYPE
        SYNTAX  OnuVoiceVlanProfileMacEntry
        ACCESS  not-accessible
        STATUS  mandatory
        DESCRIPTION
            "A collection of objects in the ONU Voice-VLAN profile MAC table."
        INDEX { onuVoiceVlanProfileMacProfileIndex, onuVoiceVlanProfileMacEntryIndex }
        ::= { onuVoiceVlanProfileMacTable 1 }

    OnuVoiceVlanProfileMacEntry ::=
        SEQUENCE {
            onuVoiceVlanProfileMacProfileIndex
                INTEGER,
            onuVoiceVlanProfileMacEntryIndex
                INTEGER,
            onuVoiceVlanProfileMacAddress
                MacAddress,
            onuVoiceVlanProfileMacPrefixLen
                INTEGER,
            onuVoiceVlanProfileMacRowStatus
                RowStatus
        }

    onuVoiceVlanProfileMacProfileIndex  OBJECT-TYPE
        SYNTAX  INTEGER
        ACCESS  read-only
        STATUS  mandatory
        DESCRIPTION
            "Index of Voice-VLAN profile."
        ::= { onuVoiceVlanProfileMacEntry 1 }

    onuVoiceVlanProfileMacEntryIndex  OBJECT-TYPE
        SYNTAX  INTEGER
        ACCESS  read-only
        STATUS  mandatory
        DESCRIPTION
            "Index of Voice-VLAN profile MAC entry."
        ::= { onuVoiceVlanProfileMacEntry 2 }

    onuVoiceVlanProfileMacAddress  OBJECT-TYPE
        SYNTAX  MacAddress
        ACCESS  read-create
        STATUS  mandatory
        DESCRIPTION
            "Address of Voice-VLAN profile MAC entry."
        ::= { onuVoiceVlanProfileMacEntry 3 }

    onuVoiceVlanProfileMacPrefixLen  OBJECT-TYPE
        SYNTAX  INTEGER (1..48)
        ACCESS  read-create
        STATUS  mandatory
        DESCRIPTION
            "Valid prefix length of Voice-VLAN profile MAC entry address."
        ::= { onuVoiceVlanProfileMacEntry 4 }

    onuVoiceVlanProfileMacRowStatus  OBJECT-TYPE
        SYNTAX  RowStatus
        ACCESS  read-create
        STATUS  mandatory
        DESCRIPTION
            "Row status of Voice-VLAN profile MAC entry."
        ::= { onuVoiceVlanProfileMacEntry 5 }

    onuVoiceVlanProfileUniTable OBJECT-TYPE
        SYNTAX  SEQUENCE OF OnuVoiceVlanProfileUniEntry
        ACCESS  not-accessible
        STATUS  mandatory
        DESCRIPTION
            "ONU Voice-VLAN profile MAC address table."
        ::= { onuVoiceVlanProfile 3 }

    onuVoiceVlanProfileUniEntry OBJECT-TYPE
        SYNTAX  OnuVoiceVlanProfileUniEntry
        ACCESS  not-accessible
        STATUS  mandatory
        DESCRIPTION
            "A collection of objects in the ONU Voice-VLAN profile MAC table."
        INDEX { onuVoiceVlanProfileUniProfileIndex, onuVoiceVlanProfileUniEntryIndex }
        ::= { onuVoiceVlanProfileUniTable 1 }

    OnuVoiceVlanProfileUniEntry ::=
        SEQUENCE {
            onuVoiceVlanProfileUniProfileIndex
                INTEGER,
            onuVoiceVlanProfileUniEntryIndex
                INTEGER,
            onuVoiceVlanProfileUniWorkMode
                INTEGER,
            onuVoiceVlanProfileUniVlanId
                INTEGER,
            onuVoiceVlanProfileUniCos
                INTEGER,
            onuVoiceVlanProfileUniDscp
                INTEGER
        }

    onuVoiceVlanProfileUniProfileIndex  OBJECT-TYPE
        SYNTAX  INTEGER
        ACCESS  read-only
        STATUS  mandatory
        DESCRIPTION
            "Index of Voice-VLAN profile."
        ::= { onuVoiceVlanProfileUniEntry 1 }

    onuVoiceVlanProfileUniEntryIndex  OBJECT-TYPE
        SYNTAX  INTEGER
        ACCESS  read-only
        STATUS  mandatory
        DESCRIPTION
            "Index of Voice-VLAN profile UNI entry."
        ::= { onuVoiceVlanProfileUniEntry 2 }

    onuVoiceVlanProfileUniWorkMode  OBJECT-TYPE
        SYNTAX  INTEGER{
                  disable(0),
                  mac-address(1),
                  vlan(2)
                }
        ACCESS  read-write
        STATUS  mandatory
        DESCRIPTION
            "Voice-VLAN working mode of UNI.
             disable - Disable Voice VLAN function.
             mac-address - Add Voice VLAN and apply QoS based on MAC address.
             vlan - Recognize Voice VLAN and apply QoS. (Voice VLAN announced by LLDP, and should be added by voice device.)
            "
        ::= { onuVoiceVlanProfileUniEntry 3 }

    onuVoiceVlanProfileUniVlanId  OBJECT-TYPE
        SYNTAX  INTEGER (2..4094)
        ACCESS  read-write
        STATUS  mandatory
        DESCRIPTION
            "Voice-VLAN ID of UNI."
        ::= { onuVoiceVlanProfileUniEntry 4 }

    onuVoiceVlanProfileUniCos  OBJECT-TYPE
        SYNTAX  INTEGER (0..8)
        ACCESS  read-write
        STATUS  mandatory
        DESCRIPTION
            "Voice-VLAN service CoS of UNI. 8 means not to modify CoS."
        ::= { onuVoiceVlanProfileUniEntry 5 }

    onuVoiceVlanProfileUniDscp  OBJECT-TYPE
        SYNTAX  INTEGER (0..128)
        ACCESS  read-write
        STATUS  mandatory
        DESCRIPTION
            "Voice-VLAN service DSCP of UNI. 128 means not to modify DSCP."
        ::= { onuVoiceVlanProfileUniEntry 6 }

-- ONU Dot1x table

    onuDot1xProfile OBJECT IDENTIFIER ::= { nmsGponProfile 20 }

    onuDot1xProfileTable OBJECT-TYPE
        SYNTAX  SEQUENCE OF OnuDot1xProfileEntry
        ACCESS  not-accessible
        STATUS  mandatory
        DESCRIPTION
            "ONU 802.1x profile table."
        ::= { onuDot1xProfile 1 }

    onuDot1xProfileEntry OBJECT-TYPE
        SYNTAX  OnuDot1xProfileEntry
        ACCESS  not-accessible
        STATUS  mandatory
        DESCRIPTION
            "A collection of objects in the ONU 802.1x profile table."
        INDEX { onuDot1xProfileIndex }
        ::= { onuDot1xProfileTable 1 }

    OnuDot1xProfileEntry ::=
        SEQUENCE {
            onuDot1xProfileIndex
                INTEGER,
            onuDot1xProfileName
                DisplayString,
            onuDot1xProfileAuthServer1
                DisplayString,
            onuDot1xProfileAuthSecret1
                DisplayString,
            onuDot1xProfileAuthServer2
                DisplayString,
            onuDot1xProfileAuthSecret2
                DisplayString,
            onuDot1xProfileRowStatus
                RowStatus
        }

    onuDot1xProfileIndex  OBJECT-TYPE
        SYNTAX  INTEGER
        ACCESS  read-only
        STATUS  mandatory
        DESCRIPTION
            "Index of 802.1x profile."
        ::= { onuDot1xProfileEntry 1 }

    onuDot1xProfileName  OBJECT-TYPE
        SYNTAX  DisplayString
        ACCESS  read-create
        STATUS  mandatory
        DESCRIPTION
            "Name of 802.1x profile."
        ::= { onuDot1xProfileEntry 2 }

    onuDot1xProfileAuthServer1  OBJECT-TYPE
        SYNTAX  DisplayString (SIZE (1..103))
        ACCESS  read-create
        STATUS  mandatory
        DESCRIPTION
            "URI of the first choice radius authentication server."
        ::= { onuDot1xProfileEntry 3 }

    onuDot1xProfileAuthSecret1  OBJECT-TYPE
        SYNTAX  DisplayString (SIZE (1..25))
        ACCESS  read-create
        STATUS  mandatory
        DESCRIPTION
            "Shared secret of the first choice radius authentication server."
        ::= { onuDot1xProfileEntry 4 }

    onuDot1xProfileAuthServer2  OBJECT-TYPE
        SYNTAX  DisplayString (SIZE (1..103))
        ACCESS  read-create
        STATUS  mandatory
        DESCRIPTION
            "URI of the second choice radius authentication server."
        ::= { onuDot1xProfileEntry 5 }

    onuDot1xProfileAuthSecret2  OBJECT-TYPE
        SYNTAX  DisplayString (SIZE (1..25))
        ACCESS  read-create
        STATUS  mandatory
        DESCRIPTION
            "Shared secret of the second choice radius authentication server."
        ::= { onuDot1xProfileEntry 6 }

    onuDot1xProfileRowStatus  OBJECT-TYPE
        SYNTAX  RowStatus
        ACCESS  read-create
        STATUS  mandatory
        DESCRIPTION
            "Row status of 802.1x profile entry."
        ::= { onuDot1xProfileEntry 7 }

    onuDot1xProfileUniTable OBJECT-TYPE
        SYNTAX  SEQUENCE OF OnuDot1xProfileUniEntry
        ACCESS  not-accessible
        STATUS  mandatory
        DESCRIPTION
            "ONU 802.1x profile UNI table."
        ::= { onuDot1xProfile 2 }

    onuDot1xProfileUniEntry OBJECT-TYPE
        SYNTAX  OnuDot1xProfileUniEntry
        ACCESS  not-accessible
        STATUS  mandatory
        DESCRIPTION
            "A collection of objects in the ONU 802.1x profile MAC table."
        INDEX { onuDot1xProfileUniProfileIndex, onuDot1xProfileUniEntryIndex }
        ::= { onuDot1xProfileUniTable 1 }

    OnuDot1xProfileUniEntry ::=
        SEQUENCE {
            onuDot1xProfileUniProfileIndex
                INTEGER,
            onuDot1xProfileUniEntryIndex
                INTEGER,
            onuDot1xProfileUniAdminStatus
                INTEGER,
            onuDot1xProfileUniMultiUserMode
                INTEGER,
            onuDot1xProfileUniGuestVlanId
                INTEGER
        }

    onuDot1xProfileUniProfileIndex  OBJECT-TYPE
        SYNTAX  INTEGER
        ACCESS  read-only
        STATUS  mandatory
        DESCRIPTION
            "Index of 802.1x profile."
        ::= { onuDot1xProfileUniEntry 1 }

    onuDot1xProfileUniEntryIndex  OBJECT-TYPE
        SYNTAX  INTEGER
        ACCESS  read-only
        STATUS  mandatory
        DESCRIPTION
            "Index of 802.1x profile UNI entry."
        ::= { onuDot1xProfileUniEntry 2 }

    onuDot1xProfileUniAdminStatus  OBJECT-TYPE
        SYNTAX  INTEGER{
                    enable(1),
                    disable(2)
                }
        ACCESS  read-create
        STATUS  mandatory
        DESCRIPTION
            "Administrative state of 802.1x authentication of UNI."
        ::= { onuDot1xProfileUniEntry 3 }

    onuDot1xProfileUniMultiUserMode  OBJECT-TYPE
        SYNTAX  INTEGER{
                  not-config(0),
                  single-user(1),
                  multiple-hosts(2),
                  multiple-auth(3)
                }
        ACCESS  read-create
        STATUS  mandatory
        DESCRIPTION
            "802.1x multiple user authentication mode of UNI.
             not-config - Keep ONU's default config.
             single-user - Single user mode.
             multiple-hosts - Multiple-hosts mode. (If one of the UNI user authenticated, all other user traffic from the UNI is permitted.)
             multiple-auth - Multiple-authentication mode. (All user from the UNI must be authenticated separately.)
            "
        ::= { onuDot1xProfileUniEntry 4 }

    onuDot1xProfileUniGuestVlanId  OBJECT-TYPE
        SYNTAX  INTEGER (0..4094)
        ACCESS  read-create
        STATUS  mandatory
        DESCRIPTION
            "802.1x guest VLAN-ID of UNI. 
            0 means not to use guest VLAN.
            If MultiUserMode is multiple-auth, guest VLAN is not supported."
        ::= { onuDot1xProfileUniEntry 5 }


-- nmsGponOltPerfObj OLT性能统计任务 1.3.6.1.4.1.3320.10.7

nmsGponOltPerfObj   OBJECT IDENTIFIER ::= { nmsGponMIB 7 }  

--配置最大历史数据量
nmsGponOltPerfStatGlobalSet   OBJECT IDENTIFIER ::= { nmsGponOltPerfObj 1 }  

          perfStat15MinMaxRecord OBJECT-TYPE
              SYNTAX  INTEGER(1..96)
              ACCESS  read-write
              STATUS  mandatory
              DESCRIPTION
                      "Performance Statistics for 15 minutes of maximal record number."
              ::= { nmsGponOltPerfStatGlobalSet 1 }

          perfStat24HourMaxRecord OBJECT-TYPE
              SYNTAX  INTEGER(1..7)
              ACCESS  read-write
              STATUS  mandatory
              DESCRIPTION
                      "Performance Statistics for 24 hours of maximal record number."
              ::= { nmsGponOltPerfStatGlobalSet 2 }

--端口性能统计开关

             nmsGponOltPerfStatPortTable OBJECT-TYPE
                 SYNTAX  SEQUENCE OF NmsGponOltPerfStatPortEntry
                 ACCESS  not-accessible
                 STATUS  mandatory
                 DESCRIPTION
                          "GPON OLT port performance statistics table."
                 ::= { nmsGponOltPerfObj 2 }

             nmsGponOltPerfStatPortEntry OBJECT-TYPE
                 SYNTAX NmsGponOltPerfStatPortEntry
                 ACCESS  not-accessible
                 STATUS  mandatory
                 DESCRIPTION
                          "GPON OLT port performance statistics table entry."
                 INDEX { perfStatIfIndex }
             ::= { nmsGponOltPerfStatPortTable 1 }

             NmsGponOltPerfStatPortEntry ::=
                 SEQUENCE {
                     perfStatIfIndex
                         INTEGER,
                     perfStat15MinEnable 
                         INTEGER,
                     perfStat24HourEnable  
                         INTEGER                    
                 }

          perfStatIfIndex OBJECT-TYPE
              SYNTAX  INTEGER
              ACCESS  read-only
              STATUS  mandatory
              DESCRIPTION
                      "Index of the table, GPON port index."
              ::= { nmsGponOltPerfStatPortEntry 1 }
                 
          perfStat15MinEnable OBJECT-TYPE
              SYNTAX  INTEGER{
                        enable(1),
                        disable(2)
                        }
              ACCESS  read-write
              STATUS  mandatory
              DESCRIPTION
                      "GPON OLT port performance statistics for 15 minutes switch: 1 Enabled, 2 Disabled. Default value is 2. "
              ::= { nmsGponOltPerfStatPortEntry 2 }
                 
          perfStat24HourEnable OBJECT-TYPE
              SYNTAX  INTEGER{
                        enable(1),
                        disable(2)
                        }
              ACCESS  read-write
              STATUS  mandatory
              DESCRIPTION
                      "GPON OLT port performance statistics for 24 hours switch: 1 Enabled, 2 Disabled. Default value is 2. "
              ::= { nmsGponOltPerfStatPortEntry 3 }
                 
--当前性能统计

             nmsGponOltPerfStatCurTable OBJECT-TYPE
                 SYNTAX  SEQUENCE OF NmsGponOltPerfStatCurEntry
                 ACCESS  not-accessible
                 STATUS  mandatory
                 DESCRIPTION
                          "GPON OLT port current performance statistics table."
                 ::= { nmsGponOltPerfObj 3 }

             nmsGponOltPerfStatCurEntry OBJECT-TYPE
                 SYNTAX NmsGponOltPerfStatCurEntry
                 ACCESS  not-accessible
                 STATUS  mandatory
                 DESCRIPTION
                          "GPON OLT port performance current statistics table entry."
                 INDEX { curStatsIfIndex }
             ::= { nmsGponOltPerfStatCurTable 1 }

             NmsGponOltPerfStatCurEntry ::=
                 SEQUENCE {
                     curStatsIfIndex
                         INTEGER,
                     curStatsInOctets 
                         Counter64,
                     curStatsInPkts  
                         Counter64,
                     curStatsInBroadcastPkts  
                         Counter64,
                     curStatsInMulticastPkts  
                         Counter64,
                     curStatsInPkts64Octets  
                         Counter64,
                     curStatsInPkts65to127Octets  
                         Counter64,
                     curStatsInPkts128to255Octets  
                         Counter64,
                     curStatsInPkts256to511Octets  
                         Counter64,
                     curStatsInPkts512to1023Octets  
                         Counter64,
                     curStatsInPkts1024to1518Octets  
                         Counter64,
                     curStatsInPkts1519toMaxOctets  
                         Counter64,
                     curStatsInUndersizePks  
                         Counter64,
                     curStatsInOversizePks  
                         Counter64,
                     curStatsInFragments  
                         Counter64,
                     curStatsInCRCErrorPkts  
                         Counter64,
                     curStatsInDropEvents  
                         Counter64,
                     curStatsInJabbers  
                         Counter64,
                     curStatsOutOctets  
                         Counter64,
                     curStatsOutPkts  
                         Counter64,
                     curStatsOutBroadcastPkts  
                         Counter64,
                     curStatsOutMulticastPkts  
                         Counter64,
                     curStatsOutPkts64Octets  
                         Counter64,
                     curStatsOutPkts65to127Octets  
                         Counter64,
                     curStatsOutPkts128to255Octets  
                         Counter64,
                     curStatsOutPkts256to511Octets  
                         Counter64,
                     curStatsOutPkts512to1023Octets  
                         Counter64,
                     curStatsOutPkts1024to1518Octets  
                         Counter64,
                     curStatsOutPkts1519toMaxOctets  
                         Counter64,
                     curStatsOutOversizePks  
                         Counter64,
                     curStatsOutDiscardPkts  
                         Counter64,
                     curStatsOutCollision  
                         Counter64,
                     curStatsStatusAndAction  
                         INTEGER                    
                 }

          curStatsIfIndex OBJECT-TYPE
              SYNTAX  INTEGER
              ACCESS  read-only
              STATUS  mandatory
              DESCRIPTION
                      "Index of the table, GPON port index."
              ::= { nmsGponOltPerfStatCurEntry 1 }               

          curStatsInOctets OBJECT-TYPE
              SYNTAX  Counter64
              ACCESS  read-only
              STATUS  mandatory
              DESCRIPTION
                      "Port current statistics of In Octets."
              ::= { nmsGponOltPerfStatCurEntry 2 }
                 
          curStatsInPkts OBJECT-TYPE
              SYNTAX  Counter64
              ACCESS  read-only
              STATUS  mandatory
              DESCRIPTION
                      "Port current statistics of In Pkts."
              ::= { nmsGponOltPerfStatCurEntry 3 }
                 
          curStatsInBroadcastPkts OBJECT-TYPE
              SYNTAX  Counter64
              ACCESS  read-only
              STATUS  mandatory
              DESCRIPTION
                      "Port current statistics of In broadcasting Pkts."
              ::= { nmsGponOltPerfStatCurEntry 4 }
                 
          curStatsInMulticastPkts OBJECT-TYPE
              SYNTAX  Counter64
              ACCESS  read-only
              STATUS  mandatory
              DESCRIPTION
                      "Port current statistics of In multicast Pkts."
              ::= { nmsGponOltPerfStatCurEntry 5 }
                 
          curStatsInPkts64Octets OBJECT-TYPE
              SYNTAX  Counter64
              ACCESS  read-only
              STATUS  mandatory
              DESCRIPTION
                      "Port current statistics of In Pkts for 64 Octets."
              ::= { nmsGponOltPerfStatCurEntry 6 }
                 
          curStatsInPkts65to127Octets OBJECT-TYPE
              SYNTAX  Counter64
              ACCESS  read-only
              STATUS  mandatory
              DESCRIPTION
                      "Port current statistics of In Pkts from 65 to 127 Octets."
              ::= { nmsGponOltPerfStatCurEntry 7 }
                 
          curStatsInPkts128to255Octets OBJECT-TYPE
              SYNTAX  Counter64
              ACCESS  read-only
              STATUS  mandatory
              DESCRIPTION
                      "Port current statistics of In Pkts from 128 to 255 Octets."
              ::= { nmsGponOltPerfStatCurEntry 8 }
                 
          curStatsInPkts256to511Octets OBJECT-TYPE
              SYNTAX  Counter64
              ACCESS  read-only
              STATUS  mandatory
              DESCRIPTION
                      "Port current statistics of In Pkts from 256 to 511 Octets."
              ::= { nmsGponOltPerfStatCurEntry 9 }
                 
          curStatsInPkts512to1023Octets OBJECT-TYPE
              SYNTAX  Counter64
              ACCESS  read-only
              STATUS  mandatory
              DESCRIPTION
                      "Port current statistics of In Pkts from 511 to 1023 Octets."
              ::= { nmsGponOltPerfStatCurEntry 10 }
                 
          curStatsInPkts1024to1518Octets OBJECT-TYPE
              SYNTAX  Counter64
              ACCESS  read-only
              STATUS  mandatory
              DESCRIPTION
                      "Port current statistics of In Pkts from 1024 to 1518 Octets."
              ::= { nmsGponOltPerfStatCurEntry 11 }
                 
          curStatsInPkts1519toMaxOctets OBJECT-TYPE
              SYNTAX  Counter64
              ACCESS  read-only
              STATUS  mandatory
              DESCRIPTION
                      "Port current statistics of In Pkts from 1519 to maximal Octets."
              ::= { nmsGponOltPerfStatCurEntry 12 }
                 
          curStatsInUndersizePks OBJECT-TYPE
              SYNTAX  Counter64
              ACCESS  read-only
              STATUS  mandatory
              DESCRIPTION
                      "Port current statistics of undersize Pkts."
              ::= { nmsGponOltPerfStatCurEntry 13 }
                 
          curStatsInOversizePks OBJECT-TYPE
              SYNTAX  Counter64
              ACCESS  read-only
              STATUS  mandatory
              DESCRIPTION
                      "Port current statistics of oversize Pkts."
              ::= { nmsGponOltPerfStatCurEntry 14 }
                 
          curStatsInFragments OBJECT-TYPE
              SYNTAX  Counter64
              ACCESS  read-only
              STATUS  mandatory
              DESCRIPTION
                      "Port current statistics of in fragments."
              ::= { nmsGponOltPerfStatCurEntry 15 }
                 
          curStatsInCRCErrorPkts OBJECT-TYPE
              SYNTAX  Counter64
              ACCESS  read-only
              STATUS  mandatory
              DESCRIPTION
                      "Port current statistics of in CRC error Pkts."
              ::= { nmsGponOltPerfStatCurEntry 16 }
                 
          curStatsInDropEvents OBJECT-TYPE
              SYNTAX  Counter64
              ACCESS  read-only
              STATUS  mandatory
              DESCRIPTION
                      "Port current statistics of in drop events."
              ::= { nmsGponOltPerfStatCurEntry 17 }
                 
          curStatsInJabbers OBJECT-TYPE
              SYNTAX  Counter64
              ACCESS  read-only
              STATUS  mandatory
              DESCRIPTION
                      "Port current statistics of in jabbers."
              ::= { nmsGponOltPerfStatCurEntry 18 }
                 
          curStatsOutOctets OBJECT-TYPE
              SYNTAX  Counter64
              ACCESS  read-only
              STATUS  mandatory
              DESCRIPTION
                      "Port current statistics of out octets."
              ::= { nmsGponOltPerfStatCurEntry 19 }
                 
          curStatsOutPkts OBJECT-TYPE
              SYNTAX  Counter64
              ACCESS  read-only
              STATUS  mandatory
              DESCRIPTION
                      "Port current statistics of out pkts."
              ::= { nmsGponOltPerfStatCurEntry 20 }
                 
          curStatsOutBroadcastPkts OBJECT-TYPE
              SYNTAX  Counter64
              ACCESS  read-only
              STATUS  mandatory
              DESCRIPTION
                      "Port current statistics of Out broadcasting Pkts."
              ::= { nmsGponOltPerfStatCurEntry 21 }
                 
          curStatsOutMulticastPkts OBJECT-TYPE
              SYNTAX  Counter64
              ACCESS  read-only
              STATUS  mandatory
              DESCRIPTION
                      "Port current statistics of Out multicast Pkts."
              ::= { nmsGponOltPerfStatCurEntry 22 }
                 
          curStatsOutPkts64Octets OBJECT-TYPE
              SYNTAX  Counter64
              ACCESS  read-only
              STATUS  mandatory
              DESCRIPTION
                      "Port current statistics of Out Pkts for 64 Octets."
              ::= { nmsGponOltPerfStatCurEntry 23 }
                 
          curStatsOutPkts65to127Octets OBJECT-TYPE
              SYNTAX  Counter64
              ACCESS  read-only
              STATUS  mandatory
              DESCRIPTION
                      "Port current statistics of Out Pkts from 65 to 127 Octets."
              ::= { nmsGponOltPerfStatCurEntry 24 }
                 
          curStatsOutPkts128to255Octets OBJECT-TYPE
              SYNTAX  Counter64
              ACCESS  read-only
              STATUS  mandatory
              DESCRIPTION
                      "Port current statistics of Out Pkts from 128 to 255 Octets."
              ::= { nmsGponOltPerfStatCurEntry 25 }
                 
          curStatsOutPkts256to511Octets OBJECT-TYPE
              SYNTAX  Counter64
              ACCESS  read-only
              STATUS  mandatory
              DESCRIPTION
                      "Port current statistics of Out Pkts from 256 to 511 Octets."
              ::= { nmsGponOltPerfStatCurEntry 26 }
                 
          curStatsOutPkts512to1023Octets OBJECT-TYPE
              SYNTAX  Counter64
              ACCESS  read-only
              STATUS  mandatory
              DESCRIPTION
                      "Port current statistics of Out Pkts from 511 to 1023 Octets."
              ::= { nmsGponOltPerfStatCurEntry 27 }
                 
          curStatsOutPkts1024to1518Octets OBJECT-TYPE
              SYNTAX  Counter64
              ACCESS  read-only
              STATUS  mandatory
              DESCRIPTION
                      "Port current statistics of Out Pkts from 1024 to 1518 Octets."
              ::= { nmsGponOltPerfStatCurEntry 28 }
                 
          curStatsOutPkts1519toMaxOctets OBJECT-TYPE
              SYNTAX  Counter64
              ACCESS  read-only
              STATUS  mandatory
              DESCRIPTION
                      "Port current statistics of Out Pkts from 1519 to maximal Octets."
              ::= { nmsGponOltPerfStatCurEntry 29 }
                 
          curStatsOutOversizePks OBJECT-TYPE
              SYNTAX  Counter64
              ACCESS  read-only
              STATUS  mandatory
              DESCRIPTION
                      "Port current statistics of oversize Pkts."
              ::= { nmsGponOltPerfStatCurEntry 30 }
                 
          curStatsOutDiscardPkts OBJECT-TYPE
              SYNTAX  Counter64
              ACCESS  read-only
              STATUS  mandatory
              DESCRIPTION
                      "Port current statistics of discard Pkts."
              ::= { nmsGponOltPerfStatCurEntry 31 }
                 
          curStatsOutCollision OBJECT-TYPE
              SYNTAX  Counter64
              ACCESS  read-only
              STATUS  mandatory
              DESCRIPTION
                      "Port current statistics of Out Collision."
              ::= { nmsGponOltPerfStatCurEntry 32 }
                 
          curStatsStatusAndAction OBJECT-TYPE
              SYNTAX  INTEGER{
                        none(1),
                        clear(2)
                              }
              ACCESS  read-write
              STATUS  mandatory
              DESCRIPTION
                      "Port current statistics status and action. "
              ::= { nmsGponOltPerfStatCurEntry 33 }
                 
--15Min性能统计

             nmsGponOltPerfStat15MinTable OBJECT-TYPE
                 SYNTAX  SEQUENCE OF NmsGponOltPerfStat15MinEntry
                 ACCESS  not-accessible
                 STATUS  mandatory
                 DESCRIPTION
                          "GPON OLT port current performance statistics table."
                 ::= { nmsGponOltPerfObj 4 }

             nmsGponOltPerfStat15MinEntry OBJECT-TYPE
                 SYNTAX NmsGponOltPerfStat15MinEntry
                 ACCESS  not-accessible
                 STATUS  mandatory
                 DESCRIPTION
                          "GPON OLT port performance current statistics table entry."
                 INDEX { stats15IfIndex,stats15Index }
             ::= { nmsGponOltPerfStat15MinTable 1 }

             NmsGponOltPerfStat15MinEntry ::=
                 SEQUENCE {
                     stats15IfIndex
                         INTEGER,
                     stats15Index
                         INTEGER,
                     stats15InOctets 
                         Counter64,
                     stats15InPkts
                         Counter64,
                     stats15InBroadcastPkts
                         Counter64,
                     stats15InMulticastPkts
                         Counter64,
                     stats15InPkts64Octets
                         Counter64,
                     stats15InPkts65to127Octets
                         Counter64,
                     stats15InPkts128to255Octets
                         Counter64,
                     stats15InPkts256to511Octets
                         Counter64,
                     stats15InPkts512to1023Octets
                         Counter64,
                     stats15InPkts1024to1518Octets
                         Counter64,
                     stats15InPkts1519toMaxOctets
                         Counter64,
                     stats15InUndersizePks
                         Counter64,
                     stats15InOversizePks
                         Counter64,
                     stats15InFragments
                         Counter64,
                     stats15InCRCErrorPkts
                         Counter64,
                     stats15InDropEvents
                         Counter64,
                     stats15InJabbers
                         Counter64,
                     stats15OutOctets
                         Counter64,
                     stats15OutPkts
                         Counter64,
                     stats15OutBroadcastPkts
                         Counter64,
                     stats15OutMulticastPkts
                         Counter64,
                     stats15OutPkts64Octets
                         Counter64,
                     stats15OutPkts65to127Octets
                         Counter64,
                     stats15OutPkts128to255Octets
                         Counter64,
                     stats15OutPkts256to511Octets
                         Counter64,
                     stats15OutPkts512to1023Octets
                         Counter64,
                     stats15OutPkts1024to1518Octets
                         Counter64,
                     stats15OutPkts1519toMaxOctets
                         Counter64,
                     stats15OutOversizePks
                         Counter64,
                     stats15OutDiscardPkts
                         Counter64,
                     stats15OutCollision
                         Counter64,
                     stats15ElapsedTime
                         INTEGER,
                     stats15EndTime
                         DateAndTime,
                     stats15StatusAndAction
                         INTEGER
        }
                       

          stats15IfIndex OBJECT-TYPE
              SYNTAX  INTEGER
              ACCESS  read-only
              STATUS  mandatory
              DESCRIPTION
                      "Index of the table, GPON port index."
              ::= { nmsGponOltPerfStat15MinEntry 1 }               

          stats15Index OBJECT-TYPE
              SYNTAX  INTEGER
              ACCESS  read-only
              STATUS  mandatory
              DESCRIPTION
                      "Index of the table, index value for each port."
              ::= { nmsGponOltPerfStat15MinEntry 2 }               

          stats15InOctets OBJECT-TYPE
              SYNTAX  Counter64
              ACCESS  read-only
              STATUS  mandatory
              DESCRIPTION
                      "Port 15 minutes statistics of In Octets."
              ::= { nmsGponOltPerfStat15MinEntry 3 }
                 
          stats15InPkts OBJECT-TYPE
              SYNTAX  Counter64
              ACCESS  read-only
              STATUS  mandatory
              DESCRIPTION
                      "Port 15 minutes statistics of In Pkts."
              ::= { nmsGponOltPerfStat15MinEntry 4 }
                 
          stats15InBroadcastPkts OBJECT-TYPE
              SYNTAX  Counter64
              ACCESS  read-only
              STATUS  mandatory
              DESCRIPTION
                      "Port 15 minutes statistics of In broadcasting Pkts."
              ::= { nmsGponOltPerfStat15MinEntry 5 }
                 
          stats15InMulticastPkts OBJECT-TYPE
              SYNTAX  Counter64
              ACCESS  read-only
              STATUS  mandatory
              DESCRIPTION
                      "Port 15 minutes statistics of In multicast Pkts."
              ::= { nmsGponOltPerfStat15MinEntry 6 }
                 
          stats15InPkts64Octets OBJECT-TYPE
              SYNTAX  Counter64
              ACCESS  read-only
              STATUS  mandatory
              DESCRIPTION
                      "Port 15 minutes statistics of In Pkts for 64 Octets."
              ::= { nmsGponOltPerfStat15MinEntry 7 }
                 
          stats15InPkts65to127Octets OBJECT-TYPE
              SYNTAX  Counter64
              ACCESS  read-only
              STATUS  mandatory
              DESCRIPTION
                      "Port 15 minutes statistics of In Pkts from 65 to 127 Octets."
              ::= { nmsGponOltPerfStat15MinEntry 8 }
                 
          stats15InPkts128to255Octets OBJECT-TYPE
              SYNTAX  Counter64
              ACCESS  read-only
              STATUS  mandatory
              DESCRIPTION
                      "Port 15 minutes statistics of In Pkts from 128 to 255 Octets."
              ::= { nmsGponOltPerfStat15MinEntry 9 }
                 
          stats15InPkts256to511Octets OBJECT-TYPE
              SYNTAX  Counter64
              ACCESS  read-only
              STATUS  mandatory
              DESCRIPTION
                      "Port 15 minutes statistics of In Pkts from 256 to 511 Octets."
              ::= { nmsGponOltPerfStat15MinEntry 10 }
                 
          stats15InPkts512to1023Octets OBJECT-TYPE
              SYNTAX  Counter64
              ACCESS  read-only
              STATUS  mandatory
              DESCRIPTION
                      "Port 15 minutes statistics of In Pkts from 511 to 1023 Octets."
              ::= { nmsGponOltPerfStat15MinEntry 11 }
                 
          stats15InPkts1024to1518Octets OBJECT-TYPE
              SYNTAX  Counter64
              ACCESS  read-only
              STATUS  mandatory
              DESCRIPTION
                      "Port 15 minutes statistics of In Pkts from 1024 to 1518 Octets."
              ::= { nmsGponOltPerfStat15MinEntry 12 }
                 
          stats15InPkts1519toMaxOctets OBJECT-TYPE
              SYNTAX  Counter64
              ACCESS  read-only
              STATUS  mandatory
              DESCRIPTION
                      "Port 15 minutes statistics of In Pkts from 1519 to maximal Octets."
              ::= { nmsGponOltPerfStat15MinEntry 13 }
                 
          stats15InUndersizePks OBJECT-TYPE
              SYNTAX  Counter64
              ACCESS  read-only
              STATUS  mandatory
              DESCRIPTION
                      "Port 15 minutes statistics of undersize Pkts."
              ::= { nmsGponOltPerfStat15MinEntry 14 }
                 
          stats15InOversizePks OBJECT-TYPE
              SYNTAX  Counter64
              ACCESS  read-only
              STATUS  mandatory
              DESCRIPTION
                      "Port 15 minutes statistics of oversize Pkts."
              ::= { nmsGponOltPerfStat15MinEntry 15 }
                 
          stats15InFragments OBJECT-TYPE
              SYNTAX  Counter64
              ACCESS  read-only
              STATUS  mandatory
              DESCRIPTION
                      "Port 15 minutes statistics of in fragments."
              ::= { nmsGponOltPerfStat15MinEntry 16 }
                 
          stats15InCRCErrorPkts OBJECT-TYPE
              SYNTAX  Counter64
              ACCESS  read-only
              STATUS  mandatory
              DESCRIPTION
                      "Port 15 minutes statistics of in CRC error Pkts."
              ::= { nmsGponOltPerfStat15MinEntry 17 }
                 
          stats15InDropEvents OBJECT-TYPE
              SYNTAX  Counter64
              ACCESS  read-only
              STATUS  mandatory
              DESCRIPTION
                      "Port 15 minutes statistics of in drop events."
              ::= { nmsGponOltPerfStat15MinEntry 18 }
                 
          stats15InJabbers OBJECT-TYPE
              SYNTAX  Counter64
              ACCESS  read-only
              STATUS  mandatory
              DESCRIPTION
                      "Port 15 minutes statistics of in jabbers."
              ::= { nmsGponOltPerfStat15MinEntry 19 }
                 
          stats15OutOctets OBJECT-TYPE
              SYNTAX  Counter64
              ACCESS  read-only
              STATUS  mandatory
              DESCRIPTION
                      "Port 15 minutes statistics of out octets."
              ::= { nmsGponOltPerfStat15MinEntry 20 }
                 
          stats15OutPkts OBJECT-TYPE
              SYNTAX  Counter64
              ACCESS  read-only
              STATUS  mandatory
              DESCRIPTION
                      "Port 15 minutes statistics of out pkts."
              ::= { nmsGponOltPerfStat15MinEntry 21 }
                 
          stats15OutBroadcastPkts OBJECT-TYPE
              SYNTAX  Counter64
              ACCESS  read-only
              STATUS  mandatory
              DESCRIPTION
                      "Port 15 minutes statistics of Out broadcasting Pkts."
              ::= { nmsGponOltPerfStat15MinEntry 22 }
                 
          stats15OutMulticastPkts OBJECT-TYPE
              SYNTAX  Counter64
              ACCESS  read-only
              STATUS  mandatory
              DESCRIPTION
                      "Port 15 minutes statistics of Out multicast Pkts."
              ::= { nmsGponOltPerfStat15MinEntry 23 }
                 
          stats15OutPkts64Octets OBJECT-TYPE
              SYNTAX  Counter64
              ACCESS  read-only
              STATUS  mandatory
              DESCRIPTION
                      "Port 15 minutes statistics of Out Pkts for 64 Octets."
              ::= { nmsGponOltPerfStat15MinEntry 24 }
                 
          stats15OutPkts65to127Octets OBJECT-TYPE
              SYNTAX  Counter64
              ACCESS  read-only
              STATUS  mandatory
              DESCRIPTION
                      "Port 15 minutes statistics of Out Pkts from 65 to 127 Octets."
              ::= { nmsGponOltPerfStat15MinEntry 25 }
                 
          stats15OutPkts128to255Octets OBJECT-TYPE
              SYNTAX  Counter64
              ACCESS  read-only
              STATUS  mandatory
              DESCRIPTION
                      "Port 15 minutes statistics of Out Pkts from 128 to 255 Octets."
              ::= { nmsGponOltPerfStat15MinEntry 26 }
                 
          stats15OutPkts256to511Octets OBJECT-TYPE
              SYNTAX  Counter64
              ACCESS  read-only
              STATUS  mandatory
              DESCRIPTION
                      "Port 15 minutes statistics of Out Pkts from 256 to 511 Octets."
              ::= { nmsGponOltPerfStat15MinEntry 27 }
                 
          stats15OutPkts512to1023Octets OBJECT-TYPE
              SYNTAX  Counter64
              ACCESS  read-only
              STATUS  mandatory
              DESCRIPTION
                      "Port 15 minutes statistics of Out Pkts from 511 to 1023 Octets."
              ::= { nmsGponOltPerfStat15MinEntry 28 }
                 
          stats15OutPkts1024to1518Octets OBJECT-TYPE
              SYNTAX  Counter64
              ACCESS  read-only
              STATUS  mandatory
              DESCRIPTION
                      "Port 15 minutes statistics of Out Pkts from 1024 to 1518 Octets."
              ::= { nmsGponOltPerfStat15MinEntry 29 }
                 
          stats15OutPkts1519toMaxOctets OBJECT-TYPE
              SYNTAX  Counter64
              ACCESS  read-only
              STATUS  mandatory
              DESCRIPTION
                      "Port 15 minutes statistics of Out Pkts from 1519 to maximal Octets."
              ::= { nmsGponOltPerfStat15MinEntry 30 }
                 
         stats15OutOversizePks OBJECT-TYPE
              SYNTAX  Counter64
              ACCESS  read-only
              STATUS  mandatory
              DESCRIPTION
                      "Port 15 minutes statistics of oversize Pkts."
              ::= { nmsGponOltPerfStat15MinEntry 31 }
                 
          stats15OutDiscardPkts OBJECT-TYPE
              SYNTAX  Counter64
              ACCESS  read-only
              STATUS  mandatory
              DESCRIPTION
                      "Port 15 minutes statistics of discard Pkts."
              ::= { nmsGponOltPerfStat15MinEntry 32 }
                 
          stats15OutCollision OBJECT-TYPE
              SYNTAX  Counter64
              ACCESS  read-only
              STATUS  mandatory
              DESCRIPTION
                      "Port 15 minutes statistics of Out Collision."
              ::= { nmsGponOltPerfStat15MinEntry 33 }

          stats15ElapsedTime OBJECT-TYPE
              SYNTAX  INTEGER
              ACCESS  read-only
              STATUS  mandatory
              DESCRIPTION
                      "Port 15 minutes statistics of elapsed time."
              ::= { nmsGponOltPerfStat15MinEntry 34 }

          stats15EndTime OBJECT-TYPE
              SYNTAX  DateAndTime
              ACCESS  read-only
              STATUS  mandatory
              DESCRIPTION
                      "Port 15 minutes statistics of end time."
              ::= { nmsGponOltPerfStat15MinEntry 35 }

          stats15StatusAndAction OBJECT-TYPE
              SYNTAX  INTEGER{
                        none(1),
                        clear(2)
                              }
              ACCESS  read-write
              STATUS  mandatory
              DESCRIPTION
                      "Port 15 minutes statistics status and action. "
              ::= { nmsGponOltPerfStat15MinEntry 36 }
                 
--24hour性能统计

             nmsGponOltPerfStat24MinTable OBJECT-TYPE
                 SYNTAX  SEQUENCE OF NmsGponOltPerfStat24MinEntry
                 ACCESS  not-accessible
                 STATUS  mandatory
                 DESCRIPTION
                          "GPON OLT port current performance statistics table."
                 ::= { nmsGponOltPerfObj 5 }

             nmsGponOltPerfStat24MinEntry OBJECT-TYPE
                 SYNTAX NmsGponOltPerfStat24MinEntry
                 ACCESS  not-accessible
                 STATUS  mandatory
                 DESCRIPTION
                          "GPON OLT port performance current statistics table entry."
                 INDEX { stats24IfIndex,stats24Index }
             ::= { nmsGponOltPerfStat24MinTable 1 }

             NmsGponOltPerfStat24MinEntry ::=
                 SEQUENCE {
                     stats24IfIndex
                         INTEGER,
                     stats24Index
                         INTEGER,
                     stats24InOctets 
                         Counter64,
                     stats24InPkts
                         Counter64,
                     stats24InBroadcastPkts
                         Counter64,
                     stats24InMulticastPkts
                         Counter64,
                     stats24InPkts64Octets
                         Counter64,
                     stats24InPkts65to127Octets
                         Counter64,
                     stats24InPkts128to255Octets
                         Counter64,
                     stats24InPkts256to511Octets
                         Counter64,
                     stats24InPkts512to1023Octets
                         Counter64,
                     stats24InPkts1024to1518Octets
                         Counter64,
                     stats24InPkts1519toMaxOctets
                         Counter64,
                     stats24InUndersizePks
                         Counter64,
                     stats24InOversizePks
                         Counter64,
                     stats24InFragments
                         Counter64,
                     stats24InCRCErrorPkts
                         Counter64,
                     stats24InDropEvents
                         Counter64,
                     stats24InJabbers
                         Counter64,
                     stats24OutOctets
                         Counter64,
                     stats24OutPkts
                         Counter64,
                     stats24OutBroadcastPkts
                         Counter64,
                     stats24OutMulticastPkts
                         Counter64,
                     stats24OutPkts64Octets
                         Counter64,
                     stats24OutPkts65to127Octets
                         Counter64,
                     stats24OutPkts128to255Octets
                         Counter64,
                     stats24OutPkts256to511Octets
                         Counter64,
                     stats24OutPkts512to1023Octets
                         Counter64,
                     stats24OutPkts1024to1518Octets
                         Counter64,
                     stats24OutPkts1519toMaxOctets
                         Counter64,
                     stats24OutOversizePks
                         Counter64,
                     stats24OutDiscardPkts
                         Counter64,
                     stats24OutCollision
                         Counter64,
                     stats24ElapsedTime
                         INTEGER,
                     stats24EndTime
                         DateAndTime,
                     stats24StatusAndAction
                         INTEGER
        }
                       

          stats24IfIndex OBJECT-TYPE
              SYNTAX  INTEGER
              ACCESS  read-only
              STATUS  mandatory
              DESCRIPTION
                      "Index of the table, GPON port index."
              ::= { nmsGponOltPerfStat24MinEntry 1 }               

          stats24Index OBJECT-TYPE
              SYNTAX  INTEGER
              ACCESS  read-only
              STATUS  mandatory
              DESCRIPTION
                      "Index of the table, index value for each port."
              ::= { nmsGponOltPerfStat24MinEntry 2 }               

          stats24InOctets OBJECT-TYPE
              SYNTAX  Counter64
              ACCESS  read-only
              STATUS  mandatory
              DESCRIPTION
                      "Port 24 hours statistics of In Octets."
              ::= { nmsGponOltPerfStat24MinEntry 3 }
                 
          stats24InPkts OBJECT-TYPE
              SYNTAX  Counter64
              ACCESS  read-only
              STATUS  mandatory
              DESCRIPTION
                      "Port 24 hours statistics of In Pkts."
              ::= { nmsGponOltPerfStat24MinEntry 4 }
                 
          stats24InBroadcastPkts OBJECT-TYPE
              SYNTAX  Counter64
              ACCESS  read-only
              STATUS  mandatory
              DESCRIPTION
                      "Port 24 hours statistics of In broadcasting Pkts."
              ::= { nmsGponOltPerfStat24MinEntry 5 }
                 
          stats24InMulticastPkts OBJECT-TYPE
              SYNTAX  Counter64
              ACCESS  read-only
              STATUS  mandatory
              DESCRIPTION
                      "Port 24 hours statistics of In multicast Pkts."
              ::= { nmsGponOltPerfStat24MinEntry 6 }
                 
          stats24InPkts64Octets OBJECT-TYPE
              SYNTAX  Counter64
              ACCESS  read-only
              STATUS  mandatory
              DESCRIPTION
                      "Port 24 hours statistics of In Pkts for 64 Octets."
              ::= { nmsGponOltPerfStat24MinEntry 7 }
                 
          stats24InPkts65to127Octets OBJECT-TYPE
              SYNTAX  Counter64
              ACCESS  read-only
              STATUS  mandatory
              DESCRIPTION
                      "Port 24 hours statistics of In Pkts from 65 to 127 Octets."
              ::= { nmsGponOltPerfStat24MinEntry 8 }
                 
          stats24InPkts128to255Octets OBJECT-TYPE
              SYNTAX  Counter64
              ACCESS  read-only
              STATUS  mandatory
              DESCRIPTION
                      "Port 24 hours statistics of In Pkts from 128 to 255 Octets."
              ::= { nmsGponOltPerfStat24MinEntry 9 }
                 
          stats24InPkts256to511Octets OBJECT-TYPE
              SYNTAX  Counter64
              ACCESS  read-only
              STATUS  mandatory
              DESCRIPTION
                      "Port 24 hours statistics of In Pkts from 256 to 511 Octets."
              ::= { nmsGponOltPerfStat24MinEntry 10 }
                 
          stats24InPkts512to1023Octets OBJECT-TYPE
              SYNTAX  Counter64
              ACCESS  read-only
              STATUS  mandatory
              DESCRIPTION
                      "Port 24 hours statistics of In Pkts from 511 to 1023 Octets."
              ::= { nmsGponOltPerfStat24MinEntry 11 }
                 
          stats24InPkts1024to1518Octets OBJECT-TYPE
              SYNTAX  Counter64
              ACCESS  read-only
              STATUS  mandatory
              DESCRIPTION
                      "Port 24 hours statistics of In Pkts from 1024 to 1518 Octets."
              ::= { nmsGponOltPerfStat24MinEntry 12 }
                 
          stats24InPkts1519toMaxOctets OBJECT-TYPE
              SYNTAX  Counter64
              ACCESS  read-only
              STATUS  mandatory
              DESCRIPTION
                      "Port 24 hours statistics of In Pkts from 1519 to maximal Octets."
              ::= { nmsGponOltPerfStat24MinEntry 13 }
                 
          stats24InUndersizePks OBJECT-TYPE
              SYNTAX  Counter64
              ACCESS  read-only
              STATUS  mandatory
              DESCRIPTION
                      "Port 24 hours statistics of undersize Pkts."
              ::= { nmsGponOltPerfStat24MinEntry 14 }
                 
          stats24InOversizePks OBJECT-TYPE
              SYNTAX  Counter64
              ACCESS  read-only
              STATUS  mandatory
              DESCRIPTION
                      "Port 24 hours statistics of oversize Pkts."
              ::= { nmsGponOltPerfStat24MinEntry 15 }
                 
          stats24InFragments OBJECT-TYPE
              SYNTAX  Counter64
              ACCESS  read-only
              STATUS  mandatory
              DESCRIPTION
                      "Port 24 hours statistics of in fragments."
              ::= { nmsGponOltPerfStat24MinEntry 16 }
                 
          stats24InCRCErrorPkts OBJECT-TYPE
              SYNTAX  Counter64
              ACCESS  read-only
              STATUS  mandatory
              DESCRIPTION
                      "Port 24 hours statistics of in CRC error Pkts."
              ::= { nmsGponOltPerfStat24MinEntry 17 }
                 
          stats24InDropEvents OBJECT-TYPE
              SYNTAX  Counter64
              ACCESS  read-only
              STATUS  mandatory
              DESCRIPTION
                      "Port 24 hours statistics of in drop events."
              ::= { nmsGponOltPerfStat24MinEntry 18 }
                 
          stats24InJabbers OBJECT-TYPE
              SYNTAX  Counter64
              ACCESS  read-only
              STATUS  mandatory
              DESCRIPTION
                      "Port 24 hours statistics of in jabbers."
              ::= { nmsGponOltPerfStat24MinEntry 19 }
                 
          stats24OutOctets OBJECT-TYPE
              SYNTAX  Counter64
              ACCESS  read-only
              STATUS  mandatory
              DESCRIPTION
                      "Port 24 hours statistics of out octets."
              ::= { nmsGponOltPerfStat24MinEntry 20 }
                 
          stats24OutPkts OBJECT-TYPE
              SYNTAX  Counter64
              ACCESS  read-only
              STATUS  mandatory
              DESCRIPTION
                      "Port 24 hours statistics of out pkts."
              ::= { nmsGponOltPerfStat24MinEntry 21 }
                 
          stats24OutBroadcastPkts OBJECT-TYPE
              SYNTAX  Counter64
              ACCESS  read-only
              STATUS  mandatory
              DESCRIPTION
                      "Port 24 hours statistics of Out broadcasting Pkts."
              ::= { nmsGponOltPerfStat24MinEntry 22 }
                 
          stats24OutMulticastPkts OBJECT-TYPE
              SYNTAX  Counter64
              ACCESS  read-only
              STATUS  mandatory
              DESCRIPTION
                      "Port 24 hours statistics of Out multicast Pkts."
              ::= { nmsGponOltPerfStat24MinEntry 23 }
                 
          stats24OutPkts64Octets OBJECT-TYPE
              SYNTAX  Counter64
              ACCESS  read-only
              STATUS  mandatory
              DESCRIPTION
                      "Port 24 hours statistics of Out Pkts for 64 Octets."
              ::= { nmsGponOltPerfStat24MinEntry 24 }
                 
          stats24OutPkts65to127Octets OBJECT-TYPE
              SYNTAX  Counter64
              ACCESS  read-only
              STATUS  mandatory
              DESCRIPTION
                      "Port 24 hours statistics of Out Pkts from 65 to 127 Octets."
              ::= { nmsGponOltPerfStat24MinEntry 25 }
                 
          stats24OutPkts128to255Octets OBJECT-TYPE
              SYNTAX  Counter64
              ACCESS  read-only
              STATUS  mandatory
              DESCRIPTION
                      "Port 24 hours statistics of Out Pkts from 128 to 255 Octets."
              ::= { nmsGponOltPerfStat24MinEntry 26 }
                 
          stats24OutPkts256to511Octets OBJECT-TYPE
              SYNTAX  Counter64
              ACCESS  read-only
              STATUS  mandatory
              DESCRIPTION
                      "Port 24 hours statistics of Out Pkts from 256 to 511 Octets."
              ::= { nmsGponOltPerfStat24MinEntry 27 }
                 
          stats24OutPkts512to1023Octets OBJECT-TYPE
              SYNTAX  Counter64
              ACCESS  read-only
              STATUS  mandatory
              DESCRIPTION
                      "Port 24 hours statistics of Out Pkts from 511 to 1023 Octets."
              ::= { nmsGponOltPerfStat24MinEntry 28 }
                 
          stats24OutPkts1024to1518Octets OBJECT-TYPE
              SYNTAX  Counter64
              ACCESS  read-only
              STATUS  mandatory
              DESCRIPTION
                      "Port 24 hours statistics of Out Pkts from 1024 to 1518 Octets."
              ::= { nmsGponOltPerfStat24MinEntry 29 }
                 
          stats24OutPkts1519toMaxOctets OBJECT-TYPE
              SYNTAX  Counter64
              ACCESS  read-only
              STATUS  mandatory
              DESCRIPTION
                      "Port 24 hours statistics of Out Pkts from 1519 to maximal Octets."
              ::= { nmsGponOltPerfStat24MinEntry 30 }
                 
         stats24OutOversizePks OBJECT-TYPE
              SYNTAX  Counter64
              ACCESS  read-only
              STATUS  mandatory
              DESCRIPTION
                      "Port 24 hours statistics of oversize Pkts."
              ::= { nmsGponOltPerfStat24MinEntry 31 }
                 
          stats24OutDiscardPkts OBJECT-TYPE
              SYNTAX  Counter64
              ACCESS  read-only
              STATUS  mandatory
              DESCRIPTION
                      "Port 24 hours statistics of discard Pkts."
              ::= { nmsGponOltPerfStat24MinEntry 32 }
                 
          stats24OutCollision OBJECT-TYPE
              SYNTAX  Counter64
              ACCESS  read-only
              STATUS  mandatory
              DESCRIPTION
                      "Port 24 hours statistics of Out Collision."
              ::= { nmsGponOltPerfStat24MinEntry 33 }

          stats24ElapsedTime OBJECT-TYPE
              SYNTAX  INTEGER
              ACCESS  read-only
              STATUS  mandatory
              DESCRIPTION
                      "Port 24 hours statistics of elapsed time."
              ::= { nmsGponOltPerfStat24MinEntry 34 }

          stats24EndTime OBJECT-TYPE
              SYNTAX  DateAndTime
              ACCESS  read-only
              STATUS  mandatory
              DESCRIPTION
                      "Port 24 hours statistics of end time."
              ::= { nmsGponOltPerfStat24MinEntry 35 }

          stats24StatusAndAction OBJECT-TYPE
              SYNTAX  INTEGER{
                        none(1),
                        clear(2)
                              }
              ACCESS  read-write
              STATUS  mandatory
              DESCRIPTION
                      "Port 24 hours statistics status and action. "
              ::= { nmsGponOltPerfStat24MinEntry 36 }
                 

--GPON igmp   nmsGponIgmpManagementObj 

    nmsGponIgmpManagementObj   OBJECT IDENTIFIER ::= { nmsGponMIB 8 }  

    gponIgmpGlobalConfigTable OBJECT-TYPE
      SYNTAX SEQUENCE OF GponIgmpGlobalConfigEntry
      MAX-ACCESS not-accessible
      STATUS current
      DESCRIPTION
        "
全局参数表
"
      ::= { nmsGponIgmpManagementObj 1 }
    
    gponIgmpGlobalConfigEntry OBJECT-TYPE
      SYNTAX GponIgmpGlobalConfigEntry
      MAX-ACCESS not-accessible
      STATUS current
      DESCRIPTION
        " "
      INDEX { gponIgmpDeviceIndex }
      ::= { gponIgmpGlobalConfigTable 1 }
    
    GponIgmpGlobalConfigEntry ::=
      SEQUENCE { 
        gponIgmpDeviceIndex
          INTEGER,
        gponIgmpMode
          INTEGER,
        gponIgmpRouterAgeingTime
          INTEGER,
        gponIgmpRouterResponseTime
          INTEGER,
        gponIgmpRobust
          INTEGER,
        gponIgmpCTCVlan
          INTEGER,
        gponIgmpProxyVlan
          INTEGER,
        gponIgmpCTCMode
          INTEGER
       }
    
    gponIgmpDeviceIndex OBJECT-TYPE
      SYNTAX INTEGER
      MAX-ACCESS not-accessible
      STATUS current
      DESCRIPTION
        "index of device. For OLT, set to corresponding device, For ONU, set to 0"
      ::= { gponIgmpGlobalConfigEntry 1 }

    gponIgmpMode OBJECT-TYPE
      SYNTAX INTEGER
        {
        proxy(1),
        controlled(2),
        disabled(3),
        snooping(4)
        }
      MAX-ACCESS read-write
      STATUS current
      DESCRIPTION
        "IGMP working mode "
      DEFVAL { disabled }
      ::= { gponIgmpGlobalConfigEntry 2 }
    
    gponIgmpRouterAgeingTime OBJECT-TYPE
      SYNTAX INTEGER
      UNITS "second"
      MAX-ACCESS read-write
      STATUS current
      DESCRIPTION
        "Router aging time, unit is second. This is used for sending general query."
      ::= { gponIgmpGlobalConfigEntry 3 }


    gponIgmpRouterResponseTime OBJECT-TYPE
      SYNTAX INTEGER
      UNITS "second"
      MAX-ACCESS read-write
      STATUS current
      DESCRIPTION
        "router response time. Unit is second. This is used for sending general query"
      ::= { gponIgmpGlobalConfigEntry 4 }

    gponIgmpRobust OBJECT-TYPE
      SYNTAX INTEGER
      MAX-ACCESS read-write
      STATUS current
      DESCRIPTION
        "Robust variable. This is used for sending general query. No less than 1"
      ::= { gponIgmpGlobalConfigEntry 5 }

    
    gponIgmpCTCVlan OBJECT-TYPE
      SYNTAX INTEGER
      MAX-ACCESS read-write
      STATUS current
      DESCRIPTION
        "
        CTC VID
        "
      ::= { gponIgmpGlobalConfigEntry 6 }
    
    gponIgmpProxyVlan OBJECT-TYPE
      SYNTAX INTEGER
      MAX-ACCESS read-write
      STATUS current
      DESCRIPTION
         "
         Proxy VID
      "
      ::= { gponIgmpGlobalConfigEntry 7 }   
      
    gponIgmpCTCMode OBJECT-TYPE
      SYNTAX INTEGER
        {
        enable(1),
        disable(2)
        }
      MAX-ACCESS read-write
      STATUS current
      DESCRIPTION
         "
         CTC mode
         "
      DEFVAL { disable }
      ::= { gponIgmpGlobalConfigEntry 8 }


-- 

    gponIgmpXlateTable OBJECT-TYPE
      SYNTAX SEQUENCE OF GponIgmpXlateEntry 
      MAX-ACCESS not-accessible
      STATUS current
      DESCRIPTION
        "
        translation table "
      ::= { nmsGponIgmpManagementObj 2 }
    
    gponIgmpXlateEntry OBJECT-TYPE
      SYNTAX GponIgmpXlateEntry
      MAX-ACCESS not-accessible
      STATUS current
      DESCRIPTION
        " "
      INDEX { gponIgmpXlateIndex }
      ::= { gponIgmpXlateTable 1 }
    
    GponIgmpXlateEntry ::=
      SEQUENCE { 
        gponIgmpXlateIndex
          INTEGER,
        gponIgmpXlateMulticastVID
          INTEGER,
        gponIgmpXlateMulticastIPAddress
          IpAddress,
        gponIgmpXlateRowStatus
          RowStatus
       }

    gponIgmpXlateIndex OBJECT-TYPE
      SYNTAX INTEGER (1..2000)
      MAX-ACCESS not-accessible
      STATUS current
      DESCRIPTION
        "
        index
"
      ::= { gponIgmpXlateEntry 1 }
    
    gponIgmpXlateMulticastVID OBJECT-TYPE
      SYNTAX INTEGER (1..4093)
      MAX-ACCESS read-create
      STATUS current
      DESCRIPTION
        "
        Xlate vs VID
"
      ::= { gponIgmpXlateEntry 2 }
    
    gponIgmpXlateMulticastIPAddress OBJECT-TYPE
      SYNTAX IpAddress
      MAX-ACCESS read-create
      STATUS current
      DESCRIPTION
        "
        Xlate的multicast IP 
"
      ::= { gponIgmpXlateEntry 3 }

    gponIgmpXlateRowStatus OBJECT-TYPE
      SYNTAX RowStatus
      MAX-ACCESS read-create
      STATUS current
      DESCRIPTION
        "
       行状态
        "
      ::= { gponIgmpXlateEntry 4 }

    gponIgmpForwardingTable OBJECT-TYPE
      SYNTAX SEQUENCE OF GponIgmpForwardingEntry
      MAX-ACCESS not-accessible
      STATUS current
      DESCRIPTION
        "
        translation table       
        "
      ::= { nmsGponIgmpManagementObj 3 }
    
    gponIgmpForwardingEntry OBJECT-TYPE
      SYNTAX GponIgmpForwardingEntry
      MAX-ACCESS not-accessible
      STATUS current
      DESCRIPTION
        " "
      INDEX { gponIgmpGroupIndex }
      ::= { gponIgmpForwardingTable 1 }    

    GponIgmpForwardingEntry ::=
      SEQUENCE { 
        gponIgmpGroupIndex
          INTEGER,
        gponIgmpGroupVID
          INTEGER,
        gponIgmpGroupIPAddress
          IpAddress,
        gponIgmpGroupPortList
          OCTET STRING,
    gponIgmpGroupMode
     INTEGER
       }

    gponIgmpGroupIndex OBJECT-TYPE
      SYNTAX INTEGER
      MAX-ACCESS not-accessible
      STATUS current
      DESCRIPTION
        "
        index
        "
      ::= { gponIgmpForwardingEntry 1 }

    gponIgmpGroupVID OBJECT-TYPE
      SYNTAX INTEGER
      MAX-ACCESS not-accessible
      STATUS current
      DESCRIPTION
        "
        Group vs VID 
"
      ::= { gponIgmpForwardingEntry 2 }

    
    gponIgmpGroupIPAddress OBJECT-TYPE
      SYNTAX IpAddress
      MAX-ACCESS not-accessible
      STATUS current
      DESCRIPTION
        "
        Group IP address
"
      ::= { gponIgmpForwardingEntry 3 }
    
    gponIgmpGroupPortList OBJECT-TYPE
      SYNTAX OCTET STRING
      MAX-ACCESS read-only
      STATUS current
      DESCRIPTION
        "
        Forwarding port list
        1. OLT
        -------------------------------------------------------------------
        It is presented by member port list. Each member port is identified
        by 4-byte format, same as TC of EponDeviceIndex. The actual length of
        this string depends of the number of member ports in the port list.
        The relationship is:
        Length of the string = 4 * (NUM of member ports)  
        For example, if device 1, port 1/2 and 2/3 is the member ports, 
        then this object will be presented as:
        01 01 02 00 01 02 03 00
        
        2. ONU
        -------------------------------------------------------------------
        It is presented by member port list. Each member port is identified
        by 2-byte format, One for slot ID, the last for port ID. The actual 
        length of this string depends of the number of member ports. If the 
        ONU is fixed (not modulized), set slot ID to 0, the NMS could ignore 
        the slot info.
        Note that, slot here shall follow the last byte definition of 
        EponCardIndex to indicate the main-slot and sub-slot index.  
        The relationship is:
        Length of the string = 2 * (NUM of member ports)  
        For example, if port 1/2 and 3/4 is the member ports of the group, 
        then the object is presented as:
        01 02 03 04       
        "
      ::= { gponIgmpForwardingEntry 4 }
    
gponIgmpGroupMode OBJECT-TYPE
      SYNTAX INTEGER
        {
            learning(1),
            static(0)
        }
      MAX-ACCESS not-accessible
      STATUS current
      DESCRIPTION
        "
        mode 
        0 static add
        1 igmp learning
        "
      ::= { gponIgmpForwardingEntry 5 }

--多播的新增部分

    gponIgmpSniMulticastVlanTable OBJECT-TYPE
      SYNTAX SEQUENCE OF GponIgmpSniMulticastVlanEntry
      MAX-ACCESS not-accessible
      STATUS current
      DESCRIPTION
        "
        translation table       
        "
      ::= { nmsGponIgmpManagementObj 4 }
    
    gponIgmpSniMulticastVlanEntry OBJECT-TYPE
      SYNTAX GponIgmpSniMulticastVlanEntry
      MAX-ACCESS not-accessible
      STATUS current
      DESCRIPTION
        " "
      INDEX { gponIgmpSniMultiVlanVid,gponIgmpSniMultiVlanDeviceIndex }
      ::= { gponIgmpSniMulticastVlanTable 1 }    

    GponIgmpSniMulticastVlanEntry ::=
      SEQUENCE { 
        gponIgmpSniMultiVlanVid
          INTEGER,
        gponIgmpSniMultiVlanDeviceIndex
          INTEGER,
        gponIgmpSniMultiVlanRowstatus
          RowStatus
       }

    gponIgmpSniMultiVlanVid OBJECT-TYPE
      SYNTAX INTEGER(1..4094)
      MAX-ACCESS read-write
      STATUS current
      DESCRIPTION
        "
          Config VLAN.
        "
      ::= { gponIgmpSniMulticastVlanEntry 1 }

    gponIgmpSniMultiVlanDeviceIndex OBJECT-TYPE
      SYNTAX INTEGER
      MAX-ACCESS read-write
      STATUS current
      DESCRIPTION
        "                                         
         Config the index of interface.
        "
      ::= { gponIgmpSniMulticastVlanEntry 2 }

    gponIgmpSniMultiVlanRowstatus OBJECT-TYPE
      SYNTAX RowStatus
      MAX-ACCESS read-create
      STATUS current
      DESCRIPTION
        "
           Table row status.
        "
      ::= { gponIgmpSniMulticastVlanEntry 3 }

-- 

    gponIgmpOltMulticastVlanTable OBJECT-TYPE
      SYNTAX SEQUENCE OF GponIgmpOltMulticastVlanEntry
      MAX-ACCESS not-accessible
      STATUS current
      DESCRIPTION
        "
        translation table       
        "
      ::= { nmsGponIgmpManagementObj 5 }
    
    gponIgmpOltMulticastVlanEntry OBJECT-TYPE
      SYNTAX GponIgmpOltMulticastVlanEntry
      MAX-ACCESS not-accessible
      STATUS current
      DESCRIPTION
        " "
      INDEX { gponIgmpMvlanIndex
,gponIgmpMvlanIgmpDeviceIndex,gponIgmpMulticastVlanId }
      ::= { gponIgmpOltMulticastVlanTable 1 }    

    GponIgmpOltMulticastVlanEntry ::=
      SEQUENCE { 
        gponIgmpMvlanIndex
          INTEGER,
        gponIgmpMvlanIgmpDeviceIndex
          INTEGER,
        gponIgmpMulticastVlanId
          INTEGER,
        gponIgmpMvlanMaxQueryResponseTime
          Counter64,
        gponIgmpMvlanRobustVariable
          INTEGER,
        gponIgmpMvlanQueryInterval
          INTEGER,
        gponIgmpMvlanLastMemberQueryInterval
          INTEGER,
        gponIgmpMvlanLastMemberQueryCount
          INTEGER,
        gponIgmpMvlanRowstatus
          INTEGER
       }

    gponIgmpMvlanIndex OBJECT-TYPE
      SYNTAX INTEGER
      MAX-ACCESS read-write
      STATUS current
      DESCRIPTION
        "
        index
        "
      ::= { gponIgmpOltMulticastVlanEntry 1 }

    gponIgmpMvlanIgmpDeviceIndex OBJECT-TYPE
      SYNTAX INTEGER
      MAX-ACCESS read-write
      STATUS current
      DESCRIPTION
        "
        index
        "
      ::= { gponIgmpOltMulticastVlanEntry 2 }

    gponIgmpMulticastVlanId OBJECT-TYPE
      SYNTAX INTEGER
      MAX-ACCESS read-write
      STATUS current
      DESCRIPTION
        "
        index
        "
      ::= { gponIgmpOltMulticastVlanEntry 3 }

    gponIgmpMvlanMaxQueryResponseTime OBJECT-TYPE
      SYNTAX Counter64
      MAX-ACCESS read-write
      STATUS current
      DESCRIPTION
        "
        index
        "
      ::= { gponIgmpOltMulticastVlanEntry 4 }

    gponIgmpMvlanRobustVariable OBJECT-TYPE
      SYNTAX INTEGER
      MAX-ACCESS read-write
      STATUS current
      DESCRIPTION
        "
        index
        "
      ::= { gponIgmpOltMulticastVlanEntry 5 }

    gponIgmpMvlanQueryInterval OBJECT-TYPE
      SYNTAX INTEGER
      MAX-ACCESS read-write
      STATUS current
      DESCRIPTION
        "
        index
        "
      ::= { gponIgmpOltMulticastVlanEntry 6 }

    gponIgmpMvlanLastMemberQueryInterval OBJECT-TYPE
      SYNTAX INTEGER
      MAX-ACCESS read-write
      STATUS current
      DESCRIPTION
        "
        index
        "
      ::= { gponIgmpOltMulticastVlanEntry 7 }

    gponIgmpMvlanLastMemberQueryCount OBJECT-TYPE
      SYNTAX INTEGER
      MAX-ACCESS read-write
      STATUS current
      DESCRIPTION
        "
        index
        "
      ::= { gponIgmpOltMulticastVlanEntry 8 }

    gponIgmpMvlanRowstatus OBJECT-TYPE
      SYNTAX INTEGER
      MAX-ACCESS read-create
      STATUS current
      DESCRIPTION
        "
        index
        "
      ::= { gponIgmpOltMulticastVlanEntry 9 }










--  GPON ONU CONFIG TEMPLATE 移植自EPON

nmsGponOnuConfigTemplate   OBJECT IDENTIFIER ::= { nmsGponMIB 9 }  

        -- 1
        -- onuConfigTemplate OBJECT IDENTIFIER ::= {nmsEponOnuBatchConfig  7 }

        
        -- 1.1
        templateTable OBJECT-TYPE
            SYNTAX SEQUENCE OF TemplateEntry
            MAX-ACCESS not-accessible
            STATUS current
            DESCRIPTION
                "Description."
            ::= { nmsGponOnuConfigTemplate 1 }

        
        -- 1.1.1
        templateEntry OBJECT-TYPE
            SYNTAX TemplateEntry
            MAX-ACCESS not-accessible
            STATUS current
            DESCRIPTION
                "Description."
            INDEX { templateName }
            ::= { templateTable 1 }

        
        TemplateEntry ::=
            SEQUENCE { 
                templateName
                    OCTET STRING,
                cmdCount
                    Integer32,
                templateRowStatus
                    RowStatus
             }

        -- 1.1.1.1
        templateName OBJECT-TYPE
            SYNTAX OCTET STRING (SIZE (0..20))
            MAX-ACCESS read-only
            STATUS current
            DESCRIPTION
                "Description."
            ::= { templateEntry 1 }

        
        -- 1.1.1.2
        cmdCount OBJECT-TYPE
            SYNTAX Integer32
            MAX-ACCESS read-only
            STATUS current
            DESCRIPTION
                "Description."
            ::= { templateEntry 2 }

        
        -- 1.1.1.3
        templateRowStatus OBJECT-TYPE
            SYNTAX RowStatus
            MAX-ACCESS read-create
            STATUS current
            DESCRIPTION
                "Description."
            ::= { templateEntry 3 }


        -- 1.2
        templateItemTable OBJECT-TYPE
            SYNTAX SEQUENCE OF TemplateItemEntry
            MAX-ACCESS not-accessible
            STATUS current
            DESCRIPTION
                "Description."
            ::= { nmsGponOnuConfigTemplate 2 }

        
        -- 1.2.1
        templateItemEntry OBJECT-TYPE
            SYNTAX TemplateItemEntry
            MAX-ACCESS not-accessible
            STATUS current
            DESCRIPTION
                "Description."
            INDEX { templateItemName, templateItemIndex }
            ::= { templateItemTable 1 }

        
        TemplateItemEntry ::=
            SEQUENCE { 
                templateItemName
                    OCTET STRING,
                templateItemIndex
                    Integer32,
                templateItemStr
                    OCTET STRING,
                templateItemRowStatus
                    RowStatus
             }

        -- 1.2.1.1
        templateItemName OBJECT-TYPE
            SYNTAX OCTET STRING (SIZE (0..20))
            MAX-ACCESS read-only
            STATUS current
            DESCRIPTION
                "Description."
            ::= { templateItemEntry 1 }

        
        -- 1.2.1.2
        templateItemIndex OBJECT-TYPE
            SYNTAX Integer32 (1..65536)
            MAX-ACCESS read-only
            STATUS current
            DESCRIPTION
                "Description."
            ::= { templateItemEntry 2 }

        
        -- 1.2.1.3
        templateItemStr OBJECT-TYPE
            SYNTAX OCTET STRING
            MAX-ACCESS read-write
            STATUS current
            DESCRIPTION
                "Description."
            ::= { templateItemEntry 3 }

        
        -- 1.2.1.4
        templateItemRowStatus OBJECT-TYPE
            SYNTAX RowStatus
            MAX-ACCESS read-create
            STATUS current
            DESCRIPTION
                "Description."
            ::= { templateItemEntry 4 }

        
        -- 1.3
        templateApplyTable OBJECT-TYPE
            SYNTAX SEQUENCE OF TemplateApplyEntry
            MAX-ACCESS not-accessible
            STATUS current
            DESCRIPTION
                "Description."
            ::= { nmsGponOnuConfigTemplate 3 }

        
        -- 1.3.1
        templateApplyEntry OBJECT-TYPE
            SYNTAX TemplateApplyEntry
            MAX-ACCESS not-accessible
            STATUS current
            DESCRIPTION
                "Description."
            INDEX { ponIndex, templateApplyName, llidBitstring }
            ::= { templateApplyTable 1 }

        
        TemplateApplyEntry ::=
            SEQUENCE { 
                ponIndex
                    Integer32,
                templateApplyName
                    OCTET STRING,
                llidBitstring
                    OCTET STRING,
                templateParameters  
                    OCTET STRING,
                templateApplyRowstatus
                    RowStatus
             }

        -- 1.3.1.1
        ponIndex OBJECT-TYPE
            SYNTAX Integer32 (1..65536)
            MAX-ACCESS read-only
            STATUS current
            DESCRIPTION
                "Description."
            ::= { templateApplyEntry 1 }

        
        -- 1.3.1.2
        templateApplyName OBJECT-TYPE
            SYNTAX OCTET STRING (SIZE (0..20))
            MAX-ACCESS read-only
            STATUS current
            DESCRIPTION
                "Description."
            ::= { templateApplyEntry 2 }

        
        -- 1.3.1.3
        llidBitstring OBJECT-TYPE
            SYNTAX OCTET STRING (SIZE (8))
            MAX-ACCESS read-only
            STATUS current
            DESCRIPTION
                "Description."
            ::= { templateApplyEntry 3 }

        -- 1.3.1.4
        templateParameters OBJECT-TYPE
            SYNTAX OCTET STRING 
            MAX-ACCESS read-write
            STATUS current
            DESCRIPTION
                "Parameter string, the maximal length is 200."
            ::= { templateApplyEntry 4 }

        -- 1.3.1.5
        templateApplyRowstatus OBJECT-TYPE
            SYNTAX RowStatus 
            MAX-ACCESS read-create
            STATUS current
            DESCRIPTION
                "row status."
            ::= { templateApplyEntry 5 } 
            
-- nmsGponVideoPortObj OLT性能统计任务 1.3.6.1.4.1.3320.10.10

nmsGponVideoPortObj   OBJECT IDENTIFIER ::= { nmsGponMIB 10 }  

--Video端口配置 
             onuVideoPortConfigTable OBJECT-TYPE
                 SYNTAX  SEQUENCE OF OnuVideoPortConfigEntry
                 ACCESS  not-accessible
                 STATUS  mandatory
                 DESCRIPTION
                          "ONU Video port config table."
                 ::= { nmsGponVideoPortObj 1 }

             onuVideoPortConfigEntry OBJECT-TYPE
                 SYNTAX OnuVideoPortConfigEntry
                 ACCESS  not-accessible
                 STATUS  mandatory
                 DESCRIPTION
                          "ONU Video port config table entry."
                 INDEX { onuVideoPortConfigDeviceIndex,  onuVideoPortConfigPortIndex}
             ::= { onuVideoPortConfigTable 1 }

             OnuVideoPortConfigEntry ::=
                 SEQUENCE {
                     onuVideoPortConfigDeviceIndex
                         INTEGER,
                     onuVideoPortConfigPortIndex 
                         INTEGER,
                     onuVideoPortConfigAdminState
                         INTEGER,
                     onuVideoPortConfigCatvProfileID
                         INTEGER,
                     onuVideoPortConfigRowStatus
                         RowStatus               
                 }

          onuVideoPortConfigDeviceIndex OBJECT-TYPE
              SYNTAX  INTEGER
              ACCESS  read-only
              STATUS  mandatory
              DESCRIPTION
                      "Index of the table, ONU port index."
              ::= { onuVideoPortConfigEntry 1 }
                 
          onuVideoPortConfigPortIndex OBJECT-TYPE
              SYNTAX  INTEGER
              ACCESS  read-only
              STATUS  mandatory
              DESCRIPTION
                      "Index of the table, video port index "
              ::= { onuVideoPortConfigEntry 2 }
              
          onuVideoPortConfigAdminState OBJECT-TYPE
              SYNTAX  INTEGER{
                        no-shutdown(1),
                        shutdown(2)
                        }              
              ACCESS  read-write
              STATUS  mandatory
              DESCRIPTION
                      "1-No shutdown  2-Shutdown "
              ::= { onuVideoPortConfigEntry 3 }
                 
          onuVideoPortConfigCatvProfileID OBJECT-TYPE
              SYNTAX  INTEGER
              ACCESS  read-write
              STATUS  mandatory
              DESCRIPTION
                      "It points to the associated Catv profile. 0 means cancel profile config."
              ::= { onuVideoPortConfigEntry 4 }
              
          onuVideoPortConfigRowStatus OBJECT-TYPE
              SYNTAX  RowStatus
              ACCESS  read-create
              STATUS  mandatory

              DESCRIPTION
                      ""
              ::= { onuVideoPortConfigEntry 5 } 
              
--ONU video端口告警陷阱
--onuVideoPortCatvAlarmTrap  OID:1.3.6.1.4.1.3320.10.10.2

    onuVideoPortCatvAlarmTrap OBJECT IDENTIFIER
                                ::= { nmsGponVideoPortObj 2 }

          onuVideoPortCatvAlarmStatus OBJECT-TYPE
              SYNTAX  INTEGER{
                              alarm(1),
                              clear(2)                              }
              ACCESS  read-only
              STATUS  mandatory
              DESCRIPTION
                      ""
              ::= { onuVideoPortCatvAlarmTrap 1 } 
              
          onuVideoPortCatvAlarmType OBJECT-TYPE
              SYNTAX  INTEGER{
                              inputlow(1),
                              inputhigh(2), 
                              outputlow(3),
                              outputhigh(4),
                              voltagelow(5),
                              voltagehigh(6),
                              temperaturelow(7),
                              temperaturehigh(8),                             }
              ACCESS  read-only
              STATUS  mandatory
              DESCRIPTION
                      ""
              ::= { onuVideoPortCatvAlarmTrap 2 }       

          onuVideoPortCatvAlarmNotification NOTIFICATION-TYPE
            OBJECTS {
                       ifIndex,
                       ifDescr,
                       onuSerialNum,
                       onuVideoPortConfigPortIndex,
                       onuVideoPortCatvAlarmType,
                       onuVideoPortCatvAlarmStatus                        }
            STATUS      current
            DESCRIPTION
            "The agent generates this notification when alarm was triggered ."
            ::= { onuVideoPortCatvAlarmTrap 3 }

--Video端口基本信息表

             onuVideoPortCatvInfoTable OBJECT-TYPE
                 SYNTAX  SEQUENCE OF OnuVideoPortCatvInfoEntry
                 ACCESS  not-accessible
                 STATUS  mandatory
                 DESCRIPTION
                          "ONU Video port information table."
                 ::= { nmsGponVideoPortObj 3 }

             onuVideoPortCatvInfoEntry OBJECT-TYPE
                 SYNTAX OnuVideoPortCatvInfoEntry
                 ACCESS  not-accessible
                 STATUS  mandatory
                 DESCRIPTION
                          "ONU Video port information table entry."
                 INDEX { onuVideoPortCatvInfoDeviceIndex,  onuVideoPortCatvInfoPortIndex}
             ::= { onuVideoPortCatvInfoTable 1 }

             OnuVideoPortCatvInfoEntry ::=
                 SEQUENCE {
                     onuVideoPortCatvInfoDeviceIndex
                         INTEGER,
                     onuVideoPortCatvInfoPortIndex 
                         INTEGER,
                     onuVideoPortCatvInfoTemperature
                         INTEGER,
                     onuVideoPortCatvInfoVoltage
                         INTEGER,
                     onuVideoPortCatvInfoRxPower
                         INTEGER,
                     onuVideoPortCatvInfoTxVoltage
                         INTEGER                
                 }

          onuVideoPortCatvInfoDeviceIndex OBJECT-TYPE
              SYNTAX  INTEGER
              ACCESS  read-only
              STATUS  mandatory
              DESCRIPTION
                      "Index of the table, ONU port index."
              ::= { onuVideoPortCatvInfoEntry 1 }
                 
          onuVideoPortCatvInfoPortIndex OBJECT-TYPE
              SYNTAX  INTEGER
              ACCESS  read-only
              STATUS  mandatory
              DESCRIPTION
                      "Index of the table, video port index "
              ::= { onuVideoPortCatvInfoEntry 2 }
              
          onuVideoPortCatvInfoTemperature OBJECT-TYPE
              SYNTAX  INTEGER           
              ACCESS  read-only
              STATUS  mandatory
              DESCRIPTION
                      ""
              ::= { onuVideoPortCatvInfoEntry 3 }
                 
          onuVideoPortCatvInfoVoltage OBJECT-TYPE
              SYNTAX  INTEGER
              ACCESS  read-only
              STATUS  mandatory
              DESCRIPTION
                      ""
              ::= { onuVideoPortCatvInfoEntry 4 }
              
          onuVideoPortCatvInfoRxPower OBJECT-TYPE
              SYNTAX  INTEGER           
              ACCESS  read-only
              STATUS  mandatory
              DESCRIPTION
                      ""
              ::= { onuVideoPortCatvInfoEntry 5 }
                 
          onuVideoPortCatvInfoTxVoltage OBJECT-TYPE
              SYNTAX  INTEGER
              ACCESS  read-only
              STATUS  mandatory
              DESCRIPTION
                      ""
              ::= { onuVideoPortCatvInfoEntry 6 }   
              
-- nmsGponWanPortObj OLT性能统计任务 1.3.6.1.4.1.3320.10.11

nmsGponWanPortObj   OBJECT IDENTIFIER ::= { nmsGponMIB 11 }  

--Wan端口基本配置

             onuWanPortConfigTable OBJECT-TYPE
                 SYNTAX  SEQUENCE OF OnuWanPortConfigEntry
                 ACCESS  not-accessible
                 STATUS  mandatory
                 DESCRIPTION
                          "ONU Wan port config table."
                 ::= { nmsGponWanPortObj 1 }

             onuWanPortConfigEntry OBJECT-TYPE
                 SYNTAX OnuWanPortConfigEntry
                 ACCESS  not-accessible
                 STATUS  mandatory
                 DESCRIPTION
                          "ONU Wan port config table entry."
                 INDEX { onuWanPortConfigDeviceIndex,  onuWanPortConfigPortIndex}
             ::= { onuWanPortConfigTable 1 }

             OnuWanPortConfigEntry ::=
                 SEQUENCE {
                     onuWanPortConfigDeviceIndex
                         INTEGER,
                     onuWanPortConfigPortIndex 
                         INTEGER,
                     onuWanPortConfigAdminState
                         INTEGER,
                     onuWanPortConfigLinkStatus
                         INTEGER,
                     onuWanPortConfigNat 
                         INTEGER,
                     onuWanPortConfigMtu
                         INTEGER,
                     onuWanPortConfigDialOnDemandTimeout
                         INTEGER,
                     onuWanPortConfigAutoGetAddress
                         INTEGER, 
                     onuWanPortConfigConnectionType
                         INTEGER,
                    onuWanPortConfigipVersion 
                         INTEGER,
                     onuWanPortConfigautoGetIpv6Address
                         INTEGER,
                     onuWanPortConfigdhcpv6PrefixDelegation
                         INTEGER,
                     onuWanPortConfigautoGetDnsAddress
                         INTEGER, 
                     onuWanPortConfiglanDhcp
                         INTEGER,
                     onuWanPortConfigRowStatus
                         RowStatus               
                 }

          onuWanPortConfigDeviceIndex OBJECT-TYPE
              SYNTAX  INTEGER
              ACCESS  read-only
              STATUS  mandatory
              DESCRIPTION
                      "Index of the table, ONU port index."
              ::= { onuWanPortConfigEntry 1 }
                 
          onuWanPortConfigPortIndex OBJECT-TYPE
              SYNTAX  INTEGER
              ACCESS  read-only
              STATUS  mandatory
              DESCRIPTION
                      "Index of the table, wan port index "
              ::= { onuWanPortConfigEntry 2 }
              
          onuWanPortConfigAdminState OBJECT-TYPE
              SYNTAX  INTEGER{
                        enable(1),
                        disable(2)
                        }
              ACCESS  read-write
              STATUS  mandatory
              DESCRIPTION
                      "1-Enable；2-Disable "
              ::= { onuWanPortConfigEntry 3 }
                 
          onuWanPortConfigLinkStatus OBJECT-TYPE
              SYNTAX  INTEGER{
                        up(1),
                        down(2)
                        }
              ACCESS  read-only
              STATUS  mandatory
              DESCRIPTION
                      "1-UP  2-DOWN"
              ::= { onuWanPortConfigEntry 4 } 
              
          onuWanPortConfigNat OBJECT-TYPE
              SYNTAX  INTEGER{
                        enable(1),
                        disable(2)
                        }
              ACCESS  read-write
              STATUS  mandatory
              DESCRIPTION
                      "1-Enable；2-Disable"
              ::= { onuWanPortConfigEntry 5 }
                 
          onuWanPortConfigMtu OBJECT-TYPE
              SYNTAX  INTEGER
              ACCESS  read-write
              STATUS  mandatory
              DESCRIPTION
                      "MTU（1-65535） "
              ::= { onuWanPortConfigEntry 6 }
              
          onuWanPortConfigDialOnDemandTimeout OBJECT-TYPE
              SYNTAX  INTEGER           
              ACCESS  read-write
              STATUS  mandatory
              DESCRIPTION
                      "On demand timeou（0-65535）:
                        0--dial always
                        1-65535--dial on demand"
              ::= { onuWanPortConfigEntry 7 }
                 
          onuWanPortConfigAutoGetAddress OBJECT-TYPE
              SYNTAX  INTEGER{
                        enable(1),
                        disable(2)
                        }
              ACCESS  read-write
              STATUS  mandatory
              DESCRIPTION
                      "1-Enable；2-Disable"
              ::= { onuWanPortConfigEntry 8 }
              
          onuWanPortConfigConnectionType OBJECT-TYPE
              SYNTAX  INTEGER{
                    bridge(1),
                    dhcp(2),
                    static(3),
                    pppoe(4),
                    pppoe_bridge(5),
                    pppoe_mix(6)
                    }           
              ACCESS  read-write
              STATUS  mandatory
              DESCRIPTION
                      "Connection Type:
                        1--bridge
                        2--DHCP
                        3--static
                        4--PPPOE
                        5--PPPOE_bridge
                        6--PPPOE_mix "
              ::= { onuWanPortConfigEntry 9 }

          onuWanPortConfigipVersion OBJECT-TYPE
              SYNTAX  INTEGER{
                        ipv4(1),
                        ipv6(2),
                        ipv4-ipv6(3)
                        }
              ACCESS  read-write
              STATUS  mandatory
              DESCRIPTION
                      "1-ipv4；2-ipv6；3-ipv4/ipv6 "
              ::= { onuWanPortConfigEntry 10 }

          onuWanPortConfigautoGetIpv6Address OBJECT-TYPE
              SYNTAX  INTEGER{
                        enable(1),
                        disable(2)
                        }
              ACCESS  read-write
              STATUS  mandatory
              DESCRIPTION
                      "1-Enable；2-Disable "
              ::= { onuWanPortConfigEntry 11 }
              
              onuWanPortConfigdhcpv6PrefixDelegation OBJECT-TYPE
              SYNTAX  INTEGER{
                        enable(1),
                        disable(2)
                        }
              ACCESS  read-write
              STATUS  mandatory
              DESCRIPTION
                      "1-Enable；2-Disable "
              ::= { onuWanPortConfigEntry 12 }
              
              onuWanPortConfigautoGetDnsAddress OBJECT-TYPE
              SYNTAX  INTEGER{
                        enable(1),
                        disable(2)
                        }
              ACCESS  read-write
              STATUS  mandatory
              DESCRIPTION
                      "1-Enable；2-Disable "
              ::= { onuWanPortConfigEntry 13 }
              
              onuWanPortConfiglanDhcp OBJECT-TYPE
              SYNTAX  INTEGER{
                        enable(1),
                        disable(2)
                        }
              ACCESS  read-write
              STATUS  mandatory
              DESCRIPTION
                      "1-Enable；2-Disable "
              ::= { onuWanPortConfigEntry 14 }
              
              
          onuWanPortConfigRowStatus OBJECT-TYPE
              SYNTAX  RowStatus
              ACCESS  read-create
              STATUS  mandatory
              DESCRIPTION
                      ""
              ::= { onuWanPortConfigEntry 15 } 
              
--Wan端口连接配置

             onuWanPortConfigLinkTable OBJECT-TYPE
                 SYNTAX  SEQUENCE OF OnuWanPortConfigLinkEntry
                 ACCESS  not-accessible
                 STATUS  mandatory
                 DESCRIPTION
                          "ONU Wan port config link table."
                 ::= { nmsGponWanPortObj 2 }

             onuWanPortConfigLinkEntry OBJECT-TYPE
                 SYNTAX OnuWanPortConfigLinkEntry
                 ACCESS  not-accessible
                 STATUS  mandatory
                 DESCRIPTION
                          "ONU Wan port config link table entry."
                 INDEX { onuWanPortConfigLinkDeviceIndex,  onuWanPortConfigLinkPortIndex}
             ::= { onuWanPortConfigLinkTable 1 }

             OnuWanPortConfigLinkEntry ::=
                 SEQUENCE {
                     onuWanPortConfigLinkDeviceIndex
                         INTEGER,
                     onuWanPortConfigLinkPortIndex 
                         INTEGER,
                     onuWanPortConfigLinkServiceTypeInternet
                         INTEGER,
                     onuWanPortConfigLinkServiceTypeVoip
                         INTEGER,
                     onuWanPortConfigLinkServiceTypeTr069
                         INTEGER,
                     onuWanPortConfigLinkServiceTypeOther
                         INTEGER,
                     onuWanPortConfigLinkRowStatus
                         RowStatus               
                 }

          onuWanPortConfigLinkDeviceIndex OBJECT-TYPE
              SYNTAX  INTEGER
              ACCESS  read-only
              STATUS  mandatory
              DESCRIPTION
                      "Index of the table, ONU port index."
              ::= { onuWanPortConfigLinkEntry 1 }
                 
          onuWanPortConfigLinkPortIndex OBJECT-TYPE
              SYNTAX  INTEGER
              ACCESS  read-only
              STATUS  mandatory
              DESCRIPTION
                      "Index of the table, wan port index "
              ::= { onuWanPortConfigLinkEntry 2 }
                 
          onuWanPortConfigLinkServiceTypeInternet OBJECT-TYPE
              SYNTAX  INTEGER{
                    enable(1),
                    disable(2)
                    }
              ACCESS  read-write
              STATUS  mandatory
              DESCRIPTION
                      "Internet Service Type:
                        1--Enable
                        2--Disable"
              ::= { onuWanPortConfigLinkEntry 3 } 
              
          onuWanPortConfigLinkServiceTypeVoip OBJECT-TYPE
              SYNTAX  INTEGER{
                    enable(1),
                    disable(2)
                    }
              ACCESS  read-write
              STATUS  mandatory
              DESCRIPTION
                      "Voip Service Type:
                        1--Enable
                        2--Disable"
              ::= { onuWanPortConfigLinkEntry 4 }
              
          onuWanPortConfigLinkServiceTypeTr069 OBJECT-TYPE
              SYNTAX  INTEGER{
                    enable(1),
                    disable(2)
                    }
              ACCESS  read-write
              STATUS  mandatory
              DESCRIPTION
                      "Tr069 Service Type:
                        1--Enable
                        2--Disable"
              ::= { onuWanPortConfigLinkEntry 5 }
              
           onuWanPortConfigLinkServiceTypeOther OBJECT-TYPE
              SYNTAX  INTEGER{
                    enable(1),
                    disable(2)
                    }
              ACCESS  read-write
              STATUS  mandatory
              DESCRIPTION
                      "Other Service Type:
                        1--Enable
                        2--Disable"
              ::= { onuWanPortConfigLinkEntry 6 }
              
           onuWanPortConfigLinkRowStatus OBJECT-TYPE
              SYNTAX  RowStatus
              ACCESS  read-create
              STATUS  mandatory
              DESCRIPTION
                      ""
              ::= { onuWanPortConfigLinkEntry 7 } 

--Wan端口Ip配置

             onuWanPortConfigIpTable OBJECT-TYPE
                 SYNTAX  SEQUENCE OF OnuWanPortConfigIpEntry
                 ACCESS  not-accessible
                 STATUS  mandatory
                 DESCRIPTION
                          "ONU Wan port config ip table."
                 ::= { nmsGponWanPortObj 3 }

             onuWanPortConfigIpEntry OBJECT-TYPE
                 SYNTAX OnuWanPortConfigIpEntry
                 ACCESS  not-accessible
                 STATUS  mandatory
                 DESCRIPTION
                          "ONU Wan port config ip table entry."
                 INDEX { onuWanPortConfigIpDeviceIndex,  onuWanPortConfigIpPortIndex}
             ::= { onuWanPortConfigIpTable 1 }

             OnuWanPortConfigIpEntry ::=
                 SEQUENCE {
                     onuWanPortConfigIpDeviceIndex
                         INTEGER,
                     onuWanPortConfigIpPortIndex 
                         INTEGER,
                     onuWanPortConfigIpAddress
                         IpAddress,
                     onuWanPortConfigIpMask
                         IpAddress,
                     onuWanPortConfigIpGateway 
                         IpAddress,
                     onuWanPortConfigIpPriDns
                         IpAddress,
                     onuWanPortConfigIpSecDns
                         IpAddress,
                     onuWanPortConfigIpRowStatus
                         RowStatus               
                 }

          onuWanPortConfigIpDeviceIndex OBJECT-TYPE
              SYNTAX  INTEGER
              ACCESS  read-only
              STATUS  mandatory
              DESCRIPTION
                      "Index of the table, ONU port index."
              ::= { onuWanPortConfigIpEntry 1 }
                 
          onuWanPortConfigIpPortIndex OBJECT-TYPE
              SYNTAX  INTEGER
              ACCESS  read-only
              STATUS  mandatory
              DESCRIPTION
                      "Index of the table, wan port index "
              ::= { onuWanPortConfigIpEntry 2 }
              
          onuWanPortConfigIpAddress OBJECT-TYPE
              SYNTAX  IpAddress              
              ACCESS  read-write
              STATUS  mandatory
              DESCRIPTION
                      "IP Address: A.A.A.A "
              ::= { onuWanPortConfigIpEntry 3 }
                 
          onuWanPortConfigIpMask OBJECT-TYPE
              SYNTAX  IpAddress
              ACCESS  read-write
              STATUS  mandatory
              DESCRIPTION
                      "Netmask: A.A.A.A"
              ::= { onuWanPortConfigIpEntry 4 } 
              
          onuWanPortConfigIpGateway OBJECT-TYPE
              SYNTAX  IpAddress
              ACCESS  read-write
              STATUS  mandatory
              DESCRIPTION
                      "Gateway: A.A.A.A"
              ::= { onuWanPortConfigIpEntry 5 }
                 
          onuWanPortConfigIpPriDns OBJECT-TYPE
              SYNTAX  IpAddress
              ACCESS  read-write
              STATUS  mandatory
              DESCRIPTION
                      "Primary DNS: A.A.A.A"
              ::= { onuWanPortConfigIpEntry 6 }
              
          onuWanPortConfigIpSecDns OBJECT-TYPE
              SYNTAX  IpAddress           
              ACCESS  read-write
              STATUS  mandatory
              DESCRIPTION
                      "Secondary DNS: A.A.A.A"
              ::= { onuWanPortConfigIpEntry 7 }
              
          onuWanPortConfigIpRowStatus OBJECT-TYPE
              SYNTAX  RowStatus
              ACCESS  read-create
              STATUS  mandatory
              DESCRIPTION
                      ""
              ::= { onuWanPortConfigIpEntry 8 } 


--Wan端口Tci配置

             onuWanPortConfigTciTable OBJECT-TYPE
                 SYNTAX  SEQUENCE OF OnuWanPortConfigTciEntry
                 ACCESS  not-accessible
                 STATUS  mandatory
                 DESCRIPTION
                          "ONU Wan port config tci table."
                 ::= { nmsGponWanPortObj 4 }

             onuWanPortConfigTciEntry OBJECT-TYPE
                 SYNTAX OnuWanPortConfigTciEntry
                 ACCESS  not-accessible
                 STATUS  mandatory
                 DESCRIPTION
                          "ONU Wan port config tci table entry."
                 INDEX { onuWanPortConfigTciDeviceIndex,  onuWanPortConfigTciPortIndex}
             ::= { onuWanPortConfigTciTable 1 }

             OnuWanPortConfigTciEntry ::=
                 SEQUENCE {
                     onuWanPortConfigTciDeviceIndex
                         INTEGER,
                     onuWanPortConfigTciPortIndex 
                         INTEGER,
                     onuWanPortConfigTciVlanId
                         INTEGER,
                     onuWanPortConfigTciPri
                         INTEGER,
                     onuWanPortConfigTciDei 
                         INTEGER,
                     onuWanPortConfigTciRowStatus
                         RowStatus               
                 }       

          onuWanPortConfigTciDeviceIndex OBJECT-TYPE
              SYNTAX  INTEGER
              ACCESS  read-only
              STATUS  mandatory
              DESCRIPTION
                      "Index of the table, ONU port index."
              ::= { onuWanPortConfigTciEntry 1 }
                 
          onuWanPortConfigTciPortIndex OBJECT-TYPE
              SYNTAX  INTEGER
              ACCESS  read-only
              STATUS  mandatory
              DESCRIPTION
                      "Index of the table, wan port index "
              ::= { onuWanPortConfigTciEntry 2 }
              
          onuWanPortConfigTciVlanId OBJECT-TYPE
              SYNTAX  INTEGER(0..4094)              
              ACCESS  read-write
              STATUS  mandatory
              DESCRIPTION
                      "Vlan ID(0-4094) 0 for vlan disable "
              ::= { onuWanPortConfigTciEntry 3 }
                 
          onuWanPortConfigTciPri OBJECT-TYPE
              SYNTAX  INTEGER(0..7)
              ACCESS  read-write
              STATUS  mandatory
              DESCRIPTION
                      "Priority(0-7)"
              ::= { onuWanPortConfigTciEntry 4 } 
              
          onuWanPortConfigTciDei OBJECT-TYPE
              SYNTAX  INTEGER(0..1)
              ACCESS  read-write
              STATUS  mandatory
              DESCRIPTION
                      "DEI(0,1)"
              ::= { onuWanPortConfigTciEntry 5 }
                     
          onuWanPortConfigTciRowStatus OBJECT-TYPE
              SYNTAX  RowStatus
              ACCESS  read-create
              STATUS  mandatory
              DESCRIPTION
                      ""
              ::= { onuWanPortConfigTciEntry 6 } 


--Wan端口绑定配置

             onuWanPortConfigBindTable OBJECT-TYPE
                 SYNTAX  SEQUENCE OF OnuWanPortConfigBindEntry
                 ACCESS  not-accessible
                 STATUS  mandatory
                 DESCRIPTION
                          "ONU Wan port config bind port table."
                 ::= { nmsGponWanPortObj 5 }

             onuWanPortConfigBindEntry OBJECT-TYPE
                 SYNTAX OnuWanPortConfigBindEntry
                 ACCESS  not-accessible
                 STATUS  mandatory
                 DESCRIPTION
                          "ONU Wan port config bind port table entry."
                 INDEX { onuWanPortConfigBindDeviceIndex,  onuWanPortConfigBindPortIndex}
             ::= { onuWanPortConfigBindTable 1 }

             OnuWanPortConfigBindEntry ::=
                 SEQUENCE {
                     onuWanPortConfigBindDeviceIndex
                         INTEGER,
                     onuWanPortConfigBindPortIndex 
                         INTEGER,
                     onuWanPortConfigBindLan1
                         INTEGER,
                     onuWanPortConfigBindLan2
                         INTEGER,
                     onuWanPortConfigBindLan3 
                         INTEGER,
                     onuWanPortConfigBindLan4
                         INTEGER,
                     onuWanPortConfigBindSsid
                         BITS,
                     onuWanPortConfigBindRowStatus
                         RowStatus               
                 }

          onuWanPortConfigBindDeviceIndex OBJECT-TYPE
              SYNTAX  INTEGER
              ACCESS  read-only
              STATUS  mandatory
              DESCRIPTION
                      "Index of the table, ONU port index."
              ::= { onuWanPortConfigBindEntry 1 }
                 
          onuWanPortConfigBindPortIndex OBJECT-TYPE
              SYNTAX  INTEGER
              ACCESS  read-only
              STATUS  mandatory
              DESCRIPTION
                      "Index of the table, wan port index "
              ::= { onuWanPortConfigBindEntry 2 }
              
          onuWanPortConfigBindLan1 OBJECT-TYPE
              SYNTAX  INTEGER{
                        enable(1),
                        disable(2)
                        }
              ACCESS  read-write
              STATUS  mandatory
              DESCRIPTION
                      "1-Enable；2-Disable "
              ::= { onuWanPortConfigBindEntry 3 }
                 
          onuWanPortConfigBindLan2 OBJECT-TYPE
              SYNTAX  INTEGER{
                        enable(1),
                        disable(2)
                        }
              ACCESS  read-write
              STATUS  mandatory
              DESCRIPTION
                      "1-Enable；2-Disable"
              ::= { onuWanPortConfigBindEntry 4 } 
              
          onuWanPortConfigBindLan3 OBJECT-TYPE
              SYNTAX  INTEGER{
                        enable(1),
                        disable(2)
                        }
              ACCESS  read-write
              STATUS  mandatory
              DESCRIPTION
                      "1-Enable；2-Disable"
              ::= { onuWanPortConfigBindEntry 5 }
                 
          onuWanPortConfigBindLan4 OBJECT-TYPE
              SYNTAX  INTEGER{
                        enable(1),
                        disable(2)
                        }
              ACCESS  read-write
              STATUS  mandatory
              DESCRIPTION
                      "1-Enable；2-Disable "
              ::= { onuWanPortConfigBindEntry 6 }
              
          onuWanPortConfigBindSsid OBJECT-TYPE
              SYNTAX  BITS{
                        ssid1(0),
                        ssid2(1),
                        ssid3(2),
                        ssid4(3),
                        ssid5(4),
                        ssid6(5),
                        ssid7(6),
                        ssid8(7)
                        }
              ACCESS  read-write
              STATUS  mandatory
              DESCRIPTION
                      "Bridge bind ssid port, 8 bits represent 8 ssid, 0 is not bind, 1 is bind "
              ::= { onuWanPortConfigBindEntry 7 }  
              
          onuWanPortConfigBindRowStatus OBJECT-TYPE
              SYNTAX  RowStatus
              ACCESS  read-create
              STATUS  mandatory
              DESCRIPTION
                      ""
              ::= { onuWanPortConfigBindEntry 8 } 


--Wan端口Pppoe配置

             onuWanPortConfigPppoeTable OBJECT-TYPE
                 SYNTAX  SEQUENCE OF OnuWanPortConfigPppoeEntry
                 ACCESS  not-accessible
                 STATUS  mandatory
                 DESCRIPTION
                          "ONU Wan port config pppoe table."
                 ::= { nmsGponWanPortObj 6 }

             onuWanPortConfigPppoeEntry OBJECT-TYPE
                 SYNTAX OnuWanPortConfigPppoeEntry
                 ACCESS  not-accessible
                 STATUS  mandatory
                 DESCRIPTION
                          "ONU Wan port config pppoe table entry."
                 INDEX { onuWanPortConfigPppoeDeviceIndex,  onuWanPortConfigPppoePortIndex}
             ::= { onuWanPortConfigPppoeTable 1 }

             OnuWanPortConfigPppoeEntry ::=
                 SEQUENCE {
                     onuWanPortConfigPppoeDeviceIndex
                         INTEGER,
                     onuWanPortConfigPppoePortIndex 
                         INTEGER,
                     onuWanPortConfigPppoeUsername
                         OCTET STRING,
                     onuWanPortConfigPppoePassword
                         OCTET STRING,
                     onuWanPortConfigPppoeRowStatus
                         RowStatus               
                 }

          onuWanPortConfigPppoeDeviceIndex OBJECT-TYPE
              SYNTAX  INTEGER
              ACCESS  read-only
              STATUS  mandatory
              DESCRIPTION
                      "Index of the table, ONU port index."
              ::= { onuWanPortConfigPppoeEntry 1 }
                 
          onuWanPortConfigPppoePortIndex OBJECT-TYPE
              SYNTAX  INTEGER
              ACCESS  read-only
              STATUS  mandatory
              DESCRIPTION
                      "Index of the table, wan port index "
              ::= { onuWanPortConfigPppoeEntry 2 }
              
          onuWanPortConfigPppoeUsername OBJECT-TYPE
              SYNTAX  OCTET STRING              
              ACCESS  read-write
              STATUS  mandatory
              DESCRIPTION
                      "PPPOE Username(1-50bytes) "
              ::= { onuWanPortConfigPppoeEntry 3 }
                 
          onuWanPortConfigPppoePassword OBJECT-TYPE
              SYNTAX  OCTET STRING
              ACCESS  read-write
              STATUS  mandatory
              DESCRIPTION
                      "PPPOE Password(1-50bytes)"
              ::= { onuWanPortConfigPppoeEntry 4 } 
              
          onuWanPortConfigPppoeRowStatus OBJECT-TYPE
              SYNTAX  RowStatus
              ACCESS  read-create
              STATUS  mandatory
              DESCRIPTION
                      ""
              ::= { onuWanPortConfigPppoeEntry 5 } 
              
              
--Wan端口connecion name配置
             onuWanPortConfigConnNameTable OBJECT-TYPE
                 SYNTAX  SEQUENCE OF OnuWanPortConfigConnNameEntry
                 ACCESS  not-accessible
                 STATUS  mandatory
                 DESCRIPTION
                          "ONU Wan port config connection name table."
                 ::= { nmsGponWanPortObj 7 }

             onuWanPortConfigConnNameEntry OBJECT-TYPE
                 SYNTAX OnuWanPortConfigConnNameEntry
                 ACCESS  not-accessible
                 STATUS  mandatory
                 DESCRIPTION
                          "ONU Wan port config pppoe table entry."
                 INDEX { onuWanPortConfigConnNameDeviceIndex,  onuWanPortConfigConnNamePortIndex}
             ::= { onuWanPortConfigConnNameTable 1 }

             OnuWanPortConfigConnNameEntry ::=
                 SEQUENCE {
                     onuWanPortConfigConnNameDeviceIndex
                         INTEGER,
                     onuWanPortConfigConnNamePortIndex 
                         INTEGER,
                     onuWanPortConfigConnName
                         OCTET STRING,
                     onuWanPortConfigConnNameRowStatus
                         RowStatus               
                 }

          onuWanPortConfigConnNameDeviceIndex OBJECT-TYPE
              SYNTAX  INTEGER
              ACCESS  read-only
              STATUS  mandatory
              DESCRIPTION
                      "Index of the table, ONU port index."
              ::= { onuWanPortConfigConnNameEntry 1 }
                 
          onuWanPortConfigConnNamePortIndex OBJECT-TYPE
              SYNTAX  INTEGER
              ACCESS  read-only
              STATUS  mandatory
              DESCRIPTION
                      "Index of the table, wan port index "
              ::= { onuWanPortConfigConnNameEntry 2 }
              
          onuWanPortConfigConnName OBJECT-TYPE
              SYNTAX  OCTET STRING              
              ACCESS  read-write
              STATUS  mandatory
              DESCRIPTION
                      "connection name(1-50bytes) "
              ::= { onuWanPortConfigConnNameEntry 3 }
                 
          onuWanPortConfigConnNameRowStatus OBJECT-TYPE
              SYNTAX  RowStatus
              ACCESS  read-create
              STATUS  mandatory
              DESCRIPTION
                      ""
              ::= { onuWanPortConfigConnNameEntry 4 } 


--Wan端口pppoe service name配置
             onuWanPortConfigPppoeServcieNameTable OBJECT-TYPE
                 SYNTAX  SEQUENCE OF OnuWanPortConfigPppoeServcieNameEntry
                 ACCESS  not-accessible
                 STATUS  mandatory
                 DESCRIPTION
                          "ONU Wan port config pppoe service name table."
                 ::= { nmsGponWanPortObj 8 }

             onuWanPortConfigPppoeServcieNameEntry OBJECT-TYPE
                 SYNTAX OnuWanPortConfigPppoeServcieNameEntry
                 ACCESS  not-accessible
                 STATUS  mandatory
                 DESCRIPTION
                          "ONU Wan port config pppoe service name table entry."
                 INDEX { onuWanPortConfigPppoeServcieNameDeviceIndex,  onuWanPortConfigPppoeServcieNamePortIndex}
             ::= { onuWanPortConfigPppoeServcieNameTable 1 }

             OnuWanPortConfigPppoeServcieNameEntry ::=
                 SEQUENCE {
                     onuWanPortConfigPppoeServcieNameDeviceIndex
                         INTEGER,
                     onuWanPortConfigPppoeServcieNamePortIndex 
                         INTEGER,
                     onuWanPortConfigPppoeServcieName
                         OCTET STRING,
                     onuWanPortConfigPppoeServcieNameRowStatus
                         RowStatus               
                 }

          onuWanPortConfigPppoeServcieNameDeviceIndex OBJECT-TYPE
              SYNTAX  INTEGER
              ACCESS  read-only
              STATUS  mandatory
              DESCRIPTION
                      "Index of the table, ONU port index."
              ::= { onuWanPortConfigPppoeServcieNameEntry 1 }
                 
          onuWanPortConfigPppoeServcieNamePortIndex OBJECT-TYPE
              SYNTAX  INTEGER
              ACCESS  read-only
              STATUS  mandatory
              DESCRIPTION
                      "Index of the table, wan port index "
              ::= { onuWanPortConfigPppoeServcieNameEntry 2 }
              
          onuWanPortConfigPppoeServcieName OBJECT-TYPE
              SYNTAX  OCTET STRING              
              ACCESS  read-write
              STATUS  mandatory
              DESCRIPTION
                      "connection name(1-50bytes) "
              ::= { onuWanPortConfigPppoeServcieNameEntry 3 }
                 
          onuWanPortConfigPppoeServcieNameRowStatus OBJECT-TYPE
              SYNTAX  RowStatus
              ACCESS  read-create
              STATUS  mandatory
              DESCRIPTION
                      ""
              ::= { onuWanPortConfigPppoeServcieNameEntry 4 } 
              
              
--Wan端口Ipv6配置

             onuWanPortConfigIpv6Table OBJECT-TYPE
                 SYNTAX  SEQUENCE OF OnuWanPortConfigIpv6Entry
                 ACCESS  not-accessible
                 STATUS  mandatory
                 DESCRIPTION
                          "ONU Wan port config ipv6 table."
                 ::= { nmsGponWanPortObj 9 }

             onuWanPortConfigIpv6Entry OBJECT-TYPE
                 SYNTAX OnuWanPortConfigIpv6Entry
                 ACCESS  not-accessible
                 STATUS  mandatory
                 DESCRIPTION
                          "ONU Wan port config ipv6 table entry."
                 INDEX { onuWanPortConfigIpv6DeviceIndex,  onuWanPortConfigIpv6PortIndex}
             ::= { onuWanPortConfigIpv6Table 1 }

             OnuWanPortConfigIpv6Entry ::=
                 SEQUENCE {
                     onuWanPortConfigIpv6DeviceIndex
                         INTEGER,
                     onuWanPortConfigIpv6PortIndex 
                         INTEGER,
                     onuWanPortConfigIpv6Address
                         InetAddressIPv6,
                     onuWanPortConfigIpv6Mask
                         InetAddressIPv6,
                     onuWanPortConfigIpv6Gateway 
                         InetAddressIPv6,
                     onuWanPortConfigIpv6PriDns
                         InetAddressIPv6,
                     onuWanPortConfigIpv6SecDns
                         InetAddressIPv6,
                     onuWanPortConfigIpv6RowStatus
                         RowStatus               
                 }

          onuWanPortConfigIpv6DeviceIndex OBJECT-TYPE
              SYNTAX  INTEGER
              ACCESS  read-only
              STATUS  mandatory
              DESCRIPTION
                      "Index of the table, ONU port index."
              ::= { onuWanPortConfigIpv6Entry 1 }
                 
          onuWanPortConfigIpv6PortIndex OBJECT-TYPE
              SYNTAX  INTEGER
              ACCESS  read-only
              STATUS  mandatory
              DESCRIPTION
                      "Index of the table, wan port index "
              ::= { onuWanPortConfigIpv6Entry 2 }
              
          onuWanPortConfigIpv6Address OBJECT-TYPE
              SYNTAX  InetAddressIPv6              
              ACCESS  read-write
              STATUS  mandatory
              DESCRIPTION
                      "Config IPv6 Address "
              ::= { onuWanPortConfigIpv6Entry 3 }
                 
          onuWanPortConfigIpv6Mask OBJECT-TYPE
              SYNTAX  InetAddressIPv6
              ACCESS  read-write
              STATUS  mandatory
              DESCRIPTION
                      "Config ipv6 Netmask "
              ::= { onuWanPortConfigIpv6Entry 4 } 
              
          onuWanPortConfigIpv6Gateway OBJECT-TYPE
              SYNTAX  InetAddressIPv6
              ACCESS  read-write
              STATUS  mandatory
              DESCRIPTION
                      "Config ipv6 Gateway "
              ::= { onuWanPortConfigIpv6Entry 5 }
                 
          onuWanPortConfigIpv6PriDns OBJECT-TYPE
              SYNTAX  InetAddressIPv6
              ACCESS  read-write
              STATUS  mandatory
              DESCRIPTION
                      "Config ipv6 Primary DNS "
              ::= { onuWanPortConfigIpv6Entry 6 }
              
          onuWanPortConfigIpv6SecDns OBJECT-TYPE
              SYNTAX  InetAddressIPv6           
              ACCESS  read-write
              STATUS  mandatory
              DESCRIPTION
                      "Config ipv6 Secondary DNS "
              ::= { onuWanPortConfigIpv6Entry 7 }
              
          onuWanPortConfigIpv6RowStatus OBJECT-TYPE
              SYNTAX  RowStatus
              ACCESS  read-create
              STATUS  mandatory
              DESCRIPTION
                      ""
              ::= { onuWanPortConfigIpv6Entry 8 } 
              
--nmsGponVoipPortObj Voip端口任务 OID:1.3.6.1.4.1.3320.10.12

nmsGponVoipPortObj   OBJECT IDENTIFIER ::= { nmsGponMIB 12 }  

-- Voip端口配置表

             onuVoipPortConfigTable OBJECT-TYPE
                 SYNTAX  SEQUENCE OF OnuVoipPortConfigEntry
                 ACCESS  not-accessible
                 STATUS  mandatory
                 DESCRIPTION
                          "Onu Voip port config table."
                 ::= { nmsGponVoipPortObj 1 }

             onuVoipPortConfigEntry OBJECT-TYPE
                 SYNTAX OnuVoipPortConfigEntry
                 ACCESS  not-accessible
                 STATUS  mandatory
                 DESCRIPTION
                          "Onu Voip port config table entry."
                 INDEX { onuVoipPortConfigDeviceIndex, onuVoipPortConfigVoipPortIndex }
             ::= { onuVoipPortConfigTable 1 }

             OnuVoipPortConfigEntry ::=
                 SEQUENCE {
                     onuVoipPortConfigDeviceIndex
                         INTEGER,
                     onuVoipPortConfigVoipPortIndex
                         INTEGER,
                     onuVoipPortConfigVoipPortAdminState
                         INTEGER,
                     onuVoipPortConfigVoipPortProfileID
                         INTEGER,
                     onuVoipPortConfigSipDialPlanProfileID
                         INTEGER,
                     onuVoipPortConfigVoipPortH248Tid
                         OCTET STRING,
                     onuVoipPortConfigVoipPortH248Mid
                         OCTET STRING,
                     onuVoipPortConfigVoipPortSipUserAor
                         OCTET STRING,
                     onuVoipPortConfigVoipPortSipDispname
                         OCTET STRING,
                     onuVoipPortConfigVoipPortSipUsername
                         OCTET STRING,
                     onuVoipPortConfigVoipPortSipPassword
                         OCTET STRING,
                     onuVoipPortConfigRowStatus
                         RowStatus
            }
                 
                 
          onuVoipPortConfigDeviceIndex OBJECT-TYPE
              SYNTAX  INTEGER
              ACCESS  read-only
              STATUS  mandatory

              DESCRIPTION
                      ""
              ::= { onuVoipPortConfigEntry 1 }


          onuVoipPortConfigVoipPortIndex OBJECT-TYPE
              SYNTAX  INTEGER
              ACCESS  read-only
              STATUS  mandatory

              DESCRIPTION
                      ""
              ::= { onuVoipPortConfigEntry 2 }

          onuVoipPortConfigVoipPortAdminState OBJECT-TYPE
              SYNTAX  INTEGER{
                               no-shutdown(1),
                               shutdown(2)
                             }
              ACCESS  read-write
              STATUS  mandatory

              DESCRIPTION
                      "1-No shutdown  2-Shutdown "
              ::= { onuVoipPortConfigEntry 3 }

          onuVoipPortConfigVoipPortProfileID OBJECT-TYPE
              SYNTAX  INTEGER
              ACCESS  read-write
              STATUS  mandatory

              DESCRIPTION
                      "It points to the associated Voip Port profile. 0 means cancel profile config. 
                      Default value is 0."
              ::= { onuVoipPortConfigEntry 4 }

          onuVoipPortConfigSipDialPlanProfileID OBJECT-TYPE
              SYNTAX  INTEGER
              ACCESS  read-write
              STATUS  mandatory

              DESCRIPTION
                      "It points to the associated Voip Sip Dial Plan profile. 0 means cancel profile config. 
                      Default value is 0."
              ::= { onuVoipPortConfigEntry 5 }

          onuVoipPortConfigVoipPortH248Tid OBJECT-TYPE
              SYNTAX  OCTET STRING
              ACCESS  read-write
              STATUS  mandatory
              DESCRIPTION
                      "ONU voip port h248 tid."
              ::= { onuVoipPortConfigEntry 6 }

          onuVoipPortConfigVoipPortH248Mid OBJECT-TYPE
              SYNTAX  OCTET STRING
              ACCESS  read-write
              STATUS  mandatory
              DESCRIPTION
                      "ONU voip port h248 mid."
              ::= { onuVoipPortConfigEntry 7 }

          onuVoipPortConfigVoipPortSipUserAor OBJECT-TYPE
              SYNTAX  OCTET STRING
              ACCESS  read-write
              STATUS  mandatory
              DESCRIPTION
                      "ONU voip port Sip User Aor."
              ::= { onuVoipPortConfigEntry 8 }

          onuVoipPortConfigVoipPortSipDispname OBJECT-TYPE
              SYNTAX  OCTET STRING
              ACCESS  read-write
              STATUS  mandatory
              DESCRIPTION
                      "ONU voip port Sip Display name."
              ::= { onuVoipPortConfigEntry 9 }

          onuVoipPortConfigVoipPortSipUsername OBJECT-TYPE
              SYNTAX  OCTET STRING
              ACCESS  read-write
              STATUS  mandatory
              DESCRIPTION
                      "ONU voip port Sip User name."
              ::= { onuVoipPortConfigEntry 10 }

          onuVoipPortConfigVoipPortSipPassword OBJECT-TYPE
              SYNTAX  OCTET STRING
              ACCESS  read-write
              STATUS  mandatory
              DESCRIPTION
                      "ONU voip port Sip Password."
              ::= { onuVoipPortConfigEntry 11 }

          onuVoipPortConfigRowStatus OBJECT-TYPE
              SYNTAX  RowStatus
              ACCESS  read-create
              STATUS  mandatory

              DESCRIPTION
                      ""
              ::= { onuVoipPortConfigEntry 12 }

-- Voip端口状态表

             onuVoipPortStatusTable OBJECT-TYPE
                 SYNTAX  SEQUENCE OF OnuVoipPortStatusEntry
                 ACCESS  not-accessible
                 STATUS  mandatory
                 DESCRIPTION
                          "Onu Voip port status table."
                 ::= { nmsGponVoipPortObj 2 }

             onuVoipPortStatusEntry OBJECT-TYPE
                 SYNTAX OnuVoipPortStatusEntry
                 ACCESS  not-accessible
                 STATUS  mandatory
                 DESCRIPTION
                          "Onu Voip port status table entry."
                 INDEX { onuVoipPortStatusDeviceIndex, onuVoipPortStatusVoipPortIndex }
             ::= { onuVoipPortStatusTable 1 }

             OnuVoipPortStatusEntry ::=
                 SEQUENCE {
                     onuVoipPortStatusDeviceIndex
                         INTEGER,
                     onuVoipPortStatusVoipPortIndex
                         INTEGER,
                     onuVoipPortStatusVoipPortAdminState
                         INTEGER,
                     onuVoipPortStatusVoipPortOperaState
                         INTEGER,
                     onuVoipPortStatusVoipPortHookState
                         INTEGER,
                     onuVoipPortStatusVoipPortVoipCodecUsed
                         INTEGER,
                     onuVoipPortStatusVoipPortVoiceServiceStatus
                         INTEGER,
                     onuVoipPortStatusVoipPortSessiontype
                         INTEGER,
                     onuVoipPortStatusVoipPortVoipLineState
                         INTEGER,
                     onuVoipPortStatusVoipPortEmergencyCallStatus
                         INTEGER
            }

          onuVoipPortStatusDeviceIndex OBJECT-TYPE
              SYNTAX  INTEGER
              ACCESS  read-only
              STATUS  mandatory

              DESCRIPTION
                      ""
              ::= { onuVoipPortStatusEntry 1 }

          onuVoipPortStatusVoipPortIndex OBJECT-TYPE
              SYNTAX  INTEGER
              ACCESS  read-only
              STATUS  mandatory

              DESCRIPTION
                      ""
              ::= { onuVoipPortStatusEntry 2 }

          onuVoipPortStatusVoipPortAdminState OBJECT-TYPE
              SYNTAX  INTEGER { no-shutdown(1), shutdown(2) }
              ACCESS  read-only
              STATUS  mandatory

              DESCRIPTION
                      "1-No shutdown, 2-shutdown"
              ::= { onuVoipPortStatusEntry 3 }

          onuVoipPortStatusVoipPortOperaState OBJECT-TYPE
              SYNTAX  INTEGER { enable(1), disable(2) }
              ACCESS  read-only
              STATUS  mandatory

              DESCRIPTION
                      "1-Enabled, 2-Disabled"
              ::= { onuVoipPortStatusEntry 4 }

          onuVoipPortStatusVoipPortHookState OBJECT-TYPE
              SYNTAX  INTEGER { on-hook(1), off-hook(2) }
              ACCESS  read-only
              STATUS  mandatory

              DESCRIPTION
                      "1-On hook, 2-Off hook"
              ::= { onuVoipPortStatusEntry 5 }

          onuVoipPortStatusVoipPortVoipCodecUsed OBJECT-TYPE
              SYNTAX  INTEGER
              ACCESS  read-only
              STATUS  mandatory

              DESCRIPTION
                      "Voip codec Used:
                      0-PCMU,
                      1-reserved,
                      2-reserved,
                      3-GSM,
                      4-ITU-T G.723,
                      5-DVI4 8kHz,
                      6-DVI4 16kHz,
                      7-LPC,
                      8-PCMA,
                      9-ITU-T G.722,
                      10-L16 2 channels,
                      11-L16 1 channel,
                      12-QCELP,
                      13-CN,
                      14-MPA,
                      15-ITU-T G.728,
                      16-DVI4 11.025kHz,
                      17-DVI4 22.050kHz,
                      18-ITU-T G.729"
              ::= { onuVoipPortStatusEntry 6 }

          onuVoipPortStatusVoipPortVoiceServiceStatus OBJECT-TYPE
              SYNTAX  INTEGER
              ACCESS  read-only
              STATUS  mandatory

              DESCRIPTION
                      "Voip voice service status:
                      0-None/initial,
                      1-Registered,
                      2-In session,
                      3-Failed registration – icmp error,
                      4-Failed registration – failed tcp,
                      5-Failed registration – failed authentication,
                      6-Failed registration – timeout,
                      7-Failed registration – server fail code,
                      8-Failed invite – icmp error,
                      9-Failed invite – failed tcp,
                      10-Failed invite – failed authentication,
                      11-Failed invite – timeout,
                      12-Failed invite – server fail code,
                      13-Port not configured,
                      14-Config done,
                      15-Disabled by switch"
              ::= { onuVoipPortStatusEntry 7 }

          onuVoipPortStatusVoipPortSessiontype OBJECT-TYPE
              SYNTAX  INTEGER
              ACCESS  read-only
              STATUS  mandatory

              DESCRIPTION
                      "Session type:
                      0-Idle/none,
                      1-2way,
                      2-3way,
                      3-Fax/modem,
                      4-Telemetry,
                      5-Conference"
              ::= { onuVoipPortStatusEntry 8 }

          onuVoipPortStatusVoipPortVoipLineState OBJECT-TYPE
              SYNTAX  INTEGER
              ACCESS  read-only
              STATUS  mandatory

              DESCRIPTION
                      "Voip line state:
                      0-Idle, on-hook,
                      1-Off-hook dial tone,
                      2-Dialling,
                      3-Ringing or FSK alerting/data,
                      4-Audible ringback,
                      5-Connecting,
                      6-Connected,
                      7-Disconnecting, audible indication,
                      8-ROH, no tone,
                      9-ROH with tone,
                      10-Unknown or undefined"
              ::= { onuVoipPortStatusEntry 9 }

          onuVoipPortStatusVoipPortEmergencyCallStatus OBJECT-TYPE
              SYNTAX  INTEGER
              ACCESS  read-only
              STATUS  mandatory

              DESCRIPTION
                      "Emergencycall status:
                      0-No emergency call in progress,
                      1-Emergency call in progress
                      "
              ::= { onuVoipPortStatusEntry 10 }

--nmsGponPSGObj PSG任务 OID:1.3.6.1.4.1.3320.10.13

nmsGponPSGObj   OBJECT IDENTIFIER ::= { nmsGponMIB 13 }  

-- PSG Config Table

         gponOltPsgConfigTable OBJECT-TYPE
             SYNTAX  SEQUENCE OF GponOltPsgConfigEntry
             ACCESS  not-accessible
             STATUS  mandatory
             DESCRIPTION
                      "PSG port configuration table."
             ::= { nmsGponPSGObj 1 }
            
         gponOltPsgConfigEntry OBJECT-TYPE
             SYNTAX  GponOltPsgConfigEntry
             ACCESS  not-accessible
             STATUS  mandatory
             DESCRIPTION
                      "PSG port configuration entry."
             INDEX { gponOltPsgConfigSlot, gponOltPsgConfigSequence }
             ::= { gponOltPsgConfigTable 1 }
            
         GponOltPsgConfigEntry ::=
             SEQUENCE {
                 gponOltPsgConfigSlot
                     INTEGER,
                 gponOltPsgConfigSequence
                     INTEGER,
                 gponOltPsgConfigIfIndex
                     INTEGER,
                 gponOltPsgConfigType
                     INTEGER,
                 gponOltPsgConfigActiveIfIndex
                     INTEGER,
                 gponOltPsgConfigStandbyIfIndex
                     INTEGER,
                 gponOltPsgConfigRowStatus
                     RowStatus,
                 gponOltPsgConfigPsgFlag
                     INTEGER
            }
            
         
         gponOltPsgConfigSlot OBJECT-TYPE
             SYNTAX  INTEGER
             ACCESS  read-only
             STATUS  mandatory
            
             DESCRIPTION
                     "slot number"
             ::= { gponOltPsgConfigEntry 1 }
            
         gponOltPsgConfigSequence OBJECT-TYPE
             SYNTAX  INTEGER
             ACCESS  read-only
             STATUS  mandatory
            
             DESCRIPTION
                     "PSG port sequnce"
             ::= { gponOltPsgConfigEntry 2 }
            
         gponOltPsgConfigIfIndex OBJECT-TYPE
             SYNTAX  INTEGER
             ACCESS  read-only
             STATUS  mandatory
            
             DESCRIPTION
                     "PSG port diID. Generated by OLT. Cannot be assigned. "
             ::= { gponOltPsgConfigEntry 3 }
            
         gponOltPsgConfigType OBJECT-TYPE
             SYNTAX  INTEGER { b-psg(1), c-psg(2) }
             ACCESS  read-create
             STATUS  mandatory
            
             DESCRIPTION
                     "PSG type"
             ::= { gponOltPsgConfigEntry 4 }
            
         gponOltPsgConfigActiveIfIndex OBJECT-TYPE
             SYNTAX  INTEGER
             ACCESS  read-create
             STATUS  mandatory
            
             DESCRIPTION
                     "PSG active member port diID of configuration, set 0 to delete active member. "
             ::= { gponOltPsgConfigEntry 5 }
            
         gponOltPsgConfigStandbyIfIndex OBJECT-TYPE
             SYNTAX  INTEGER
             ACCESS  read-create
             STATUS  mandatory
            
             DESCRIPTION
                     "PSG standby member port diID of configuration, set 0 to delete standby member. "
             ::= { gponOltPsgConfigEntry 6 }
            
         gponOltPsgConfigRowStatus OBJECT-TYPE
             SYNTAX  RowStatus
             ACCESS  read-create
             STATUS  mandatory
            
             DESCRIPTION
                     ""
             ::= { gponOltPsgConfigEntry 7 }
            
         gponOltPsgConfigPsgFlag OBJECT-TYPE
             SYNTAX  INTEGER { single-slot(0), multi-slot(1), dual-parenting(2) }
             ACCESS  read-create
             STATUS  mandatory
            
             DESCRIPTION
                     "PSG config flag. "
             ::= { gponOltPsgConfigEntry 8 }
            
-- PSG Status Table

         gponOltPsgStatusTable OBJECT-TYPE
             SYNTAX  SEQUENCE OF GponOltPsgStatusEntry
             ACCESS  not-accessible
             STATUS  mandatory
             DESCRIPTION
                      "PSG port status table."
             ::= { nmsGponPSGObj 2 }
            
         gponOltPsgStatusEntry OBJECT-TYPE
             SYNTAX  GponOltPsgStatusEntry
             ACCESS  not-accessible
             STATUS  mandatory
             DESCRIPTION
                      "PSG port status entry."
             INDEX { gponOltPsgStatusIfIndex }
             ::= { gponOltPsgStatusTable 1 }
            
         GponOltPsgStatusEntry ::=
             SEQUENCE {
                 gponOltPsgStatusIfIndex
                     INTEGER,
                 gponOltPsgStatusSlot
                     INTEGER,
                 gponOltPsgStatusSequence
                     INTEGER,
                 gponOltPsgStatusCurrentActiveIfIndex
                     INTEGER,
                 gponOltPsgStatusCurrentStandbyIfIndex
                     INTEGER,
                 gponOltPsgStatusSwitchOver
                     INTEGER
            }
            
         gponOltPsgStatusIfIndex OBJECT-TYPE
             SYNTAX  INTEGER
             ACCESS  read-only
             STATUS  mandatory
            
             DESCRIPTION
                     "PSG port diID. "
             ::= { gponOltPsgStatusEntry 1 }
         
         gponOltPsgStatusSlot OBJECT-TYPE
             SYNTAX  INTEGER
             ACCESS  read-only
             STATUS  mandatory
            
             DESCRIPTION
                     "slot number"
             ::= { gponOltPsgStatusEntry 2 }
            
         gponOltPsgStatusSequence OBJECT-TYPE
             SYNTAX  INTEGER
             ACCESS  read-only
             STATUS  mandatory
            
             DESCRIPTION
                     "PSG port sequnce"
             ::= { gponOltPsgStatusEntry 3 }
            
         gponOltPsgStatusCurrentActiveIfIndex OBJECT-TYPE
             SYNTAX  INTEGER
             ACCESS  read-only
             STATUS  mandatory
            
             DESCRIPTION
                     "PSG active-working member port diID"
             ::= { gponOltPsgStatusEntry 4 }
            
         gponOltPsgStatusCurrentStandbyIfIndex OBJECT-TYPE
             SYNTAX  INTEGER
             ACCESS  read-only
             STATUS  mandatory
            
             DESCRIPTION
                     "PSG standby-working  member port diID"
             ::= { gponOltPsgStatusEntry 5 }
            
         gponOltPsgStatusSwitchOver OBJECT-TYPE
             SYNTAX  INTEGER { switch-over(1) }
             ACCESS  read-write
             STATUS  mandatory
            
             DESCRIPTION
                     "PSG member working status switch over manually"
             ::= { gponOltPsgStatusEntry 6 }
            
         gponOltPsgAlarmTrap OBJECT IDENTIFIER
                                ::= { nmsGponPSGObj 3 }
         
         gponOltPsgAlarmSwitchOver NOTIFICATION-TYPE
             OBJECTS {
                        gponOltPsgStatusIfIndex,
                        gponOltPsgStatusSlot,
                        gponOltPsgStatusSequence,
                        ifDescr,
                        gponOltPsgStatusCurrentActiveIfIndex,
                        gponOltPsgStatusCurrentStandbyIfIndex
                    }
             STATUS  mandatory
             DESCRIPTION
                     "The agent generates this notification when alarm was triggered ."
            ::= { gponOltPsgAlarmTrap 1 }    
            
-- Dual-parenting PSG Port Info Table

         gponOltDpPsgPortInfoTable OBJECT-TYPE
             SYNTAX  SEQUENCE OF GponOltDpPsgPortInfoEntry
             ACCESS  not-accessible
             STATUS  mandatory
             DESCRIPTION
                      "Dual-parenting PSG port info table."
             ::= { nmsGponPSGObj 4 }
            
         gponOltDpPsgPortInfoEntry OBJECT-TYPE
             SYNTAX  GponOltDpPsgPortInfoEntry
             ACCESS  not-accessible
             STATUS  mandatory
             DESCRIPTION
                      "Dual-parenting PSG port info entry."
             INDEX { gponOltDpPsgPortInfoIfIndex }
             ::= { gponOltDpPsgPortInfoTable 1 }
            
         GponOltDpPsgPortInfoEntry ::=
             SEQUENCE {
                 gponOltDpPsgPortInfoIfIndex
                     INTEGER,
                 gponOltDpPsgPortInfoSlot
                     INTEGER,
                 gponOltDpPsgPortInfoSequence
                     INTEGER,
                 gponOltDpPsgPortInfoLocalMemberIfIndex
                     INTEGER,
                 gponOltDpPsgPortInfoPeerMemberSlot
                     INTEGER,
                 gponOltDpPsgPortInfoPeerMemberSequence
                     INTEGER,
                 gponOltDpPsgPortInfoPeerMemberDiID
                     INTEGER,
                 gponOltDpPsgPortInfoLocalStatus
                     INTEGER,
                 gponOltDpPsgPortInfoPeerStatus
                     INTEGER,
                 gponOltDpPsgPortInfoLocalSynStatus
                     INTEGER,
                 gponOltDpPsgPortInfoPeerSynStatus
                     INTEGER
            }
            
         gponOltDpPsgPortInfoIfIndex OBJECT-TYPE
             SYNTAX  INTEGER
             ACCESS  read-only
             STATUS  mandatory
            
             DESCRIPTION
                     "Dual-parenting PSG port diID. "
             ::= { gponOltDpPsgPortInfoEntry 1 }
         
         gponOltDpPsgPortInfoSlot OBJECT-TYPE
             SYNTAX  INTEGER
             ACCESS  read-only
             STATUS  mandatory
            
             DESCRIPTION
                     "Dual-parenting PSG slot number"
             ::= { gponOltDpPsgPortInfoEntry 2 }
            
         gponOltDpPsgPortInfoSequence OBJECT-TYPE
             SYNTAX  INTEGER(0..64)
             ACCESS  read-only
             STATUS  mandatory
            
             DESCRIPTION
                     "Dual-parenting PSG port sequnce"
             ::= { gponOltDpPsgPortInfoEntry 3 }
            
         gponOltDpPsgPortInfoLocalMemberIfIndex OBJECT-TYPE
             SYNTAX  INTEGER
             ACCESS  read-only
             STATUS  mandatory
            
             DESCRIPTION
                     "Dual-parenting PSG local member port diID"
             ::= { gponOltDpPsgPortInfoEntry 4 }
            
         gponOltDpPsgPortInfoPeerMemberSlot OBJECT-TYPE
             SYNTAX  INTEGER
             ACCESS  read-only
             STATUS  mandatory
            
             DESCRIPTION
                     "Dual-parenting PSG peer member port slot"
             ::= { gponOltDpPsgPortInfoEntry 5 }
            
         gponOltDpPsgPortInfoPeerMemberSequence OBJECT-TYPE
             SYNTAX  INTEGER 
             ACCESS  read-only
             STATUS  mandatory
            
             DESCRIPTION
                     "Dual-parenting PSG peer member port sequence"
             ::= { gponOltDpPsgPortInfoEntry 6 } 
         
         gponOltDpPsgPortInfoPeerMemberDiID OBJECT-TYPE
             SYNTAX  INTEGER 
             ACCESS  read-only
             STATUS  mandatory
            
             DESCRIPTION
                     "Dual-parenting PSG peer member port diID"
             ::= { gponOltDpPsgPortInfoEntry 7 }
             
         gponOltDpPsgPortInfoLocalStatus OBJECT-TYPE
             SYNTAX  INTEGER {  none(0),
								active(1),
								standby(2),
								shutdown(3),
								standby-downgrade(4)
							 }
             ACCESS  read-only
             STATUS  mandatory
            
             DESCRIPTION
                     "Dual-parenting PSG local psg status"
             ::= { gponOltDpPsgPortInfoEntry 8 }
             
         gponOltDpPsgPortInfoPeerStatus OBJECT-TYPE
             SYNTAX  INTEGER {  
             					none(0),
								active(1),
								standby(2),
								shutdown(3),
								standby-downgrade(4)
							 }
             ACCESS  read-only
             STATUS  mandatory
            
             DESCRIPTION
                     "Dual-parenting PSG peer psg status"
             ::= { gponOltDpPsgPortInfoEntry 9 }
         
         gponOltDpPsgPortInfoLocalSynStatus OBJECT-TYPE
             SYNTAX  INTEGER { 	
             					none(5),
								psg-syn-success(6),
								psg-local(7),
								psg-create(8),
								member-create(9),
								psg-not-create(10),
								no-member(11),
								onu-config-diff(12),
								error(13) 
							 }
             ACCESS  read-only
             STATUS  mandatory
            
             DESCRIPTION
                     "Dual-parenting PSG local psg  syn status"
             ::= { gponOltDpPsgPortInfoEntry 10 }
             
         gponOltDpPsgPortInfoPeerSynStatus OBJECT-TYPE
             SYNTAX  INTEGER {
             					none(5),
								psg-syn-success(6),
								psg-local(7),
								psg-create(8),
								member-create(9),
								psg-not-create(10),
								no-member(11),
								onu-config-diff(12),
								error(13) 
							 }
             ACCESS  read-only
             STATUS  mandatory
            
             DESCRIPTION
                     "Dual-parenting PSG local psg syn status"
             ::= { gponOltDpPsgPortInfoEntry 11 }
                         
-- Dual-parenting PSG Config           
gponOltDpPsgConfig         OBJECT IDENTIFIER ::= { nmsGponPSGObj 5 }
		gponOltDpPsgConfigLocalAddr OBJECT-TYPE
		    SYNTAX  IpAddress
		    ACCESS  read-write
		    STATUS  mandatory
		    DESCRIPTION
		            "Dual-parenting PSG local address"
		    ::= { gponOltDpPsgConfig 1 } 
		
		gponOltDpPsgConfigLocalPort OBJECT-TYPE
		    SYNTAX  INTEGER(1..65535)
		    ACCESS  read-write
		    STATUS  mandatory
		    DESCRIPTION
		            "Dual-parenting PSG local port,1-65535(default 4250)"
		    ::= { gponOltDpPsgConfig 2 } 
		    
		    
		gponOltDpPsgConfigPeerAddr OBJECT-TYPE
		    SYNTAX  IpAddress
		    ACCESS  read-write
		    STATUS  mandatory
		    DESCRIPTION
		            "Dual-parenting PSG peer address"
		    ::= { gponOltDpPsgConfig 3 } 
		       
		gponOltDpPsgConfigPeerPort OBJECT-TYPE
		    SYNTAX  INTEGER(1..65535)
		    ACCESS  read-write
		    STATUS  mandatory
		    DESCRIPTION
		            "Dual-parenting PSG peer port,1-65535(default 4250)"
		    ::= { gponOltDpPsgConfig 4 } 
		    
		gponOltDpPsgConfigLocalSplitAction OBJECT-TYPE
		    SYNTAX  INTEGER {
		    					none(0),
		    				    keep(1),
								force-active(2),
								force-standby(3)
		    				}
		    ACCESS  read-write
		    STATUS  mandatory
		    DESCRIPTION
		            "Dual-parenting PSG local split-action"
		    ::= { gponOltDpPsgConfig 5 } 
		    
		gponOltDpPsgConfigPeerSplitAction OBJECT-TYPE
		    SYNTAX  INTEGER {
		    					none(0),
		    				    keep(1),
								force-active(2),
								force-standby(3)
		    				}
		    ACCESS  read-only
		    STATUS  mandatory
		    DESCRIPTION
		            "Dual-parenting PSG peer split-action"
		    ::= { gponOltDpPsgConfig 6 }		    
		    
		gponOltDpPsgConfigPri OBJECT-TYPE
		    SYNTAX  INTEGER {   
		    					none(0),
		    				    low(1),
								high(2)
		    				}
		    ACCESS  read-only
		    STATUS  mandatory
		    DESCRIPTION
		            "Dual-parenting PSG local priority(compare cpu MAC)"
		    ::= { gponOltDpPsgConfig 7 } 		    
		    
		gponOltDpPsgConfigEnable OBJECT-TYPE
		    SYNTAX  INTEGER {
		    				    disable(0),
								enable(1)
		    				}
		    ACCESS  read-write
		    STATUS  mandatory
		    DESCRIPTION
		            "Dual-parenting PSG enable/disable"
		    ::= { gponOltDpPsgConfig 8 }		    
		    
		gponOltDpPsgConfigState OBJECT-TYPE
		    SYNTAX  INTEGER {
		    				    disable(0),
								enable(1),
								connected(2),
								enable-local(3),
								nego-fail(4),
								dp-established(5)
		    				}
		    ACCESS  read-only
		    STATUS  mandatory
		    DESCRIPTION
		            "Dual-parenting PSG establish state"
		    ::= { gponOltDpPsgConfig 9 }		    
		    
		gponOltDpPsgConfigSubmit OBJECT-TYPE
		    SYNTAX  INTEGER
		    ACCESS  read-write
		    STATUS  mandatory
		    DESCRIPTION
		            "Submit dual-parenting PSG config"
		    ::= { gponOltDpPsgConfig 10 }
		    
-- Dual-parenting PSG Uplink Port Config Table

         gponDpPsgUplinkPortCfgTable OBJECT-TYPE
             SYNTAX  SEQUENCE OF GponDpPsgUplinkPortCfgEntry
             ACCESS  not-accessible
             STATUS  mandatory
             DESCRIPTION
                      "Dual-parenting PSG Uplink port Config table."
             ::= { nmsGponPSGObj 6 }
            
         gponDpPsgUplinkPortCfgEntry OBJECT-TYPE
             SYNTAX  GponDpPsgUplinkPortCfgEntry
             ACCESS  not-accessible
             STATUS  mandatory
             DESCRIPTION
                      "Dual-parenting PSG Uplink port config entry."
             INDEX { gponDpPsgUplinkPortCfgIfIndex }
             ::= { gponDpPsgUplinkPortCfgTable 1 }
            
         GponDpPsgUplinkPortCfgEntry ::=
             SEQUENCE {
                 gponDpPsgUplinkPortCfgIfIndex
                     INTEGER,
                 gponDpPsgUplinkPortCfgPsgList
                     OCTET STRING,
                 gponDpPsgUplinkPortCfgRowStatus
                     RowStatus
            }
            
         gponDpPsgUplinkPortCfgIfIndex OBJECT-TYPE
             SYNTAX  INTEGER
             ACCESS  read-only
             STATUS  mandatory
            
             DESCRIPTION
                     "Uplink port Ifindex"
             ::= { gponDpPsgUplinkPortCfgEntry 1 }
         
         gponDpPsgUplinkPortCfgPsgList OBJECT-TYPE
             SYNTAX  OCTET STRING
             ACCESS  read-write
             STATUS  mandatory
            
             DESCRIPTION
                     "Dual-parenting PSG port list(1-100byte)"
             ::= { gponDpPsgUplinkPortCfgEntry 2 }
            
         gponDpPsgUplinkPortCfgRowStatus OBJECT-TYPE
             SYNTAX  RowStatus
             ACCESS  read-create
             STATUS  mandatory
            
             DESCRIPTION
                     ""
             ::= { gponDpPsgUplinkPortCfgEntry 3 }
                                     
-- Dual-parenting PSG Uplink-check Global Param              
gponOltDpPsgUplinkGlParam         OBJECT IDENTIFIER ::= { nmsGponPSGObj 7 }
		gponOltDpPsgUplinkGlParamPingCount OBJECT-TYPE
		    SYNTAX  INTEGER(1..10)
		    ACCESS  read-write
		    STATUS  mandatory
		    DESCRIPTION
		            "Uplink check ping count every time,1-10,default 3"
		    ::= { gponOltDpPsgUplinkGlParam 1 } 
		
		gponOltDpPsgUplinkGlParamFailCount OBJECT-TYPE
		    SYNTAX  INTEGER(1..10)
		    ACCESS  read-write
		    STATUS  mandatory
		    DESCRIPTION
		            "Fail count every time for fail result,1-10,default 3"
		    ::= { gponOltDpPsgUplinkGlParam 2 } 
		    
		    
		gponOltDpPsgUplinkGlParamWaitTime OBJECT-TYPE
		    SYNTAX  INTEGER(1..1000)
		    ACCESS  read-write
		    STATUS  mandatory
		    DESCRIPTION
		            "Wait time for ping response,1-1000(unit 10ms,default 100,1000ms)"
		    ::= { gponOltDpPsgUplinkGlParam 3 } 
		       
		gponOltDpPsgUplinkGlParamFastInterval OBJECT-TYPE
		    SYNTAX  INTEGER(1..120)
		    ACCESS  read-write
		    STATUS  mandatory
		    DESCRIPTION
		            "Fast interval between ping operation,1-120(unit 1s,default 1s)"
		    ::= { gponOltDpPsgUplinkGlParam 4 } 
		    
		gponOltDpPsgUplinkGlParamSlowInterval OBJECT-TYPE
		    SYNTAX  INTEGER(1..120)
		    ACCESS  read-write
		    STATUS  mandatory
		    DESCRIPTION
		            "Slow interval between ping operation,1-120(unit 1s,default 15s)"
		    ::= { gponOltDpPsgUplinkGlParam 5 } 
		    
		gponOltDpPsgUplinkGlParamRecoverTimes OBJECT-TYPE
		    SYNTAX  INTEGER(1..10)
		    ACCESS  read-write
		    STATUS  mandatory
		    DESCRIPTION
		            "Continue successful ping times for recover,1-10(default 5)"
		    ::= { gponOltDpPsgUplinkGlParam 6 }		    
		    
		gponOltDpPsgUplinkGlParamBreakTimes OBJECT-TYPE
		    SYNTAX  INTEGER(1..10)
		    ACCESS  read-write
		    STATUS  mandatory
		    DESCRIPTION
		            "Continue failed ping times for break,1-10(default 2)"
		    ::= { gponOltDpPsgUplinkGlParam 7 } 		    
		    
		gponOltDpPsgUplinkGlParamSubmit OBJECT-TYPE
		    SYNTAX  INTEGER
		    ACCESS  read-write
		    STATUS  mandatory
		    DESCRIPTION
		            "Submit uplink global param config"
		    ::= { gponOltDpPsgUplinkGlParam 8 }		    
		    
-- Dual-parenting PSG Uplink-check Global Config Table

         gponOltDpPsgUplinkGlCfgTable OBJECT-TYPE
             SYNTAX  SEQUENCE OF GponOltDpPsgUplinkGlCfgEntry
             ACCESS  not-accessible
             STATUS  mandatory
             DESCRIPTION
                      "Dual-parenting PSG Uplink-check Global Config table."
             ::= { nmsGponPSGObj 8 }
            
         gponOltDpPsgUplinkGlCfgEntry OBJECT-TYPE
             SYNTAX  GponOltDpPsgUplinkGlCfgEntry
             ACCESS  not-accessible
             STATUS  mandatory
             DESCRIPTION
                      "Dual-parenting PSG Uplink-check global config entry."
             INDEX { gponOltDpPsgUplinkGlCfgAddr }
             ::= { gponOltDpPsgUplinkGlCfgTable 1 }
            
         GponOltDpPsgUplinkGlCfgEntry ::=
             SEQUENCE {
                 gponOltDpPsgUplinkGlCfgAddr
                     IpAddress,
                 gponOltDpPsgUplinkGlCfgPsgList
                     OCTET STRING,
                 gponOltDpPsgUplinkGlCfgRowStatus
                     RowStatus
            }
            
         gponOltDpPsgUplinkGlCfgAddr OBJECT-TYPE
             SYNTAX  IpAddress
             ACCESS  read-only
             STATUS  mandatory
            
             DESCRIPTION
                     "Uplink check group address"
             ::= { gponOltDpPsgUplinkGlCfgEntry 1 }
         
         gponOltDpPsgUplinkGlCfgPsgList OBJECT-TYPE
             SYNTAX  OCTET STRING
             ACCESS  read-write
             STATUS  mandatory
            
             DESCRIPTION
                     "Dual-parenting PSG port list(1-100byte)"
             ::= { gponOltDpPsgUplinkGlCfgEntry 2 }
            
         gponOltDpPsgUplinkGlCfgRowStatus OBJECT-TYPE
             SYNTAX  RowStatus
             ACCESS  read-create
             STATUS  mandatory
            
             DESCRIPTION
                     ""
             ::= { gponOltDpPsgUplinkGlCfgEntry 3 } 
	    
	
-- nmsGponWifiPortObj OLT WIFI 配置 1.3.6.1.4.1.3320.10.14

nmsGponWifiPortObj   OBJECT IDENTIFIER ::= { nmsGponMIB 14 }  

--Wifi端口通用配置

             onuWifiConfigTable OBJECT-TYPE
                 SYNTAX  SEQUENCE OF OnuWifiConfigEntry
                 ACCESS  not-accessible
                 STATUS  mandatory
                 DESCRIPTION
                          "ONU Wifi common config table."
                 ::= { nmsGponWifiPortObj 1 }

             onuWifiConfigEntry OBJECT-TYPE
                 SYNTAX OnuWifiConfigEntry
                 ACCESS  not-accessible
                 STATUS  mandatory
                 DESCRIPTION
                          "ONU Wifi common config table entry."
                 INDEX { onuWifiConfigDeviceIndex, onuWifiConfigPortIndex }
             ::= { onuWifiConfigTable 1 }

            OnuWifiConfigEntry ::=
                 SEQUENCE {
                     onuWifiConfigDeviceIndex
                         INTEGER,
                     onuWifiConfigPortIndex 
                         INTEGER,
                     onuWifiConfigSsidPointers
                         INTEGER,
                     onuWifiConfigWifiMode
                         INTEGER,
                     onuWifiConfigWifiHardwareVersion 
                         OCTET STRING,
                     onuWifiConfigWifiSoftwareVersion
                         OCTET STRING,
                     onuWifiConfigItems
                         INTEGER,
                     onuWifiConfigTxpowerMode
                         INTEGER, 
                     onuWifiConfigTxRate
                         INTEGER,
                    onuWifiConfigCtrlband 
                         INTEGER,
                     onuWifiConfigWlanEnable
                         INTEGER,
                     onuWifiConfigRowStatus
                         RowStatus               
                 }

          onuWifiConfigDeviceIndex OBJECT-TYPE
              SYNTAX  INTEGER
              ACCESS  read-only
              STATUS  mandatory
              DESCRIPTION
                      "Index of the table, ONU port index."
              ::= { onuWifiConfigEntry 1 }
                 
          onuWifiConfigPortIndex OBJECT-TYPE
              SYNTAX  INTEGER{
                        w_2_4_G_mode(1),
                        w_5G_mode(2)
                        }     
              ACCESS  read-only
              STATUS  mandatory
              DESCRIPTION
                      "Index of the table, 2.4G(1) or 5G(2) wifi port index "
              ::= { onuWifiConfigEntry 2 }
              
          onuWifiConfigSsidPointers OBJECT-TYPE
              SYNTAX  INTEGER         
              ACCESS  read-only
              STATUS  mandatory
              DESCRIPTION
                      "valid ssid id mask ssid(1-8) from LSB to HSB"
              ::= { onuWifiConfigEntry 3 }
                 
          onuWifiConfigWifiMode OBJECT-TYPE
              SYNTAX  INTEGER{
                        w_2_4_G_mode(1),
                        w_5G_mode(2)
                        }     
              ACCESS  read-only
              STATUS  mandatory
              DESCRIPTION
                      "1-2.4G  2-5G"
              ::= { onuWifiConfigEntry 4 } 
              
          onuWifiConfigWifiHardwareVersion OBJECT-TYPE
              SYNTAX  OCTET STRING
              ACCESS  read-only
              STATUS  mandatory
              DESCRIPTION
                      "wifi hardware version"
              ::= { onuWifiConfigEntry 5 }
                 
          onuWifiConfigWifiSoftwareVersion OBJECT-TYPE
              SYNTAX  OCTET STRING
              ACCESS  read-only
              STATUS  mandatory
              DESCRIPTION
                      "wifi software version"
              ::= { onuWifiConfigEntry 6 }
              
          onuWifiConfigItems OBJECT-TYPE
              SYNTAX  INTEGER           
              ACCESS  read-only
              STATUS  mandatory
              DESCRIPTION
                      "total valid ssid number"
              ::= { onuWifiConfigEntry 7 }
                 
          onuWifiConfigTxpowerMode OBJECT-TYPE
              SYNTAX  INTEGER{
                        percent_15(1),
                        percent_35(2),
                        percent_50(3),
                        percent_70(4),
                        percent_100(5)
                        }
              ACCESS  read-write
              STATUS  mandatory
              DESCRIPTION
                      "wifi txpower mode"
              ::= { onuWifiConfigEntry 8 }
              
          onuWifiConfigTxRate OBJECT-TYPE
              SYNTAX  INTEGER
              ACCESS  read-write
              STATUS  mandatory
              DESCRIPTION
                      "Wifi TxRate:
                        0--1M
                        1--2M
                        2--5.5M
                        3--6M
                        4--9M
                        5--11M
                        7--12M
                        8--18M
                        9--24M
                        10--36M
                        11--48M
                        12--54M
                        13-28 --MC0~MC15 (for 2.4G)
                        29-38 --NSS1-MCS0~NSS1-MCS9 (for 5G)
                        39-48 --NSS2-MCS0~NSS2-MCS9 (for 5G)"
              ::= { onuWifiConfigEntry 9 }

          onuWifiConfigCtrlband OBJECT-TYPE
              SYNTAX  INTEGER{
                        lower(0),
                        upper(1),
                        auto(2)
                        }              
              ACCESS  read-write
              STATUS  mandatory
              DESCRIPTION
                      "Wifi ctrlband:
                      0-lower(2.4G)；1-upper(2.4)；2-auto(5G) "
              ::= { onuWifiConfigEntry 10 }

          onuWifiConfigWlanEnable OBJECT-TYPE
              SYNTAX  INTEGER{
                        enable(1),
                        disable(2)
                        }              
              ACCESS  read-write
              STATUS  mandatory
              DESCRIPTION
                      "WlanEnable:
                      1-Enable；2-Disable "
              ::= { onuWifiConfigEntry 11 }              
              
              onuWifiConfigRowStatus OBJECT-TYPE
              SYNTAX  RowStatus
              ACCESS  read-create
              STATUS  mandatory
              DESCRIPTION
                      ""
              ::= { onuWifiConfigEntry 12 }
              
--Wifi channel配置

             onuWifiConfigChannelTable OBJECT-TYPE
                 SYNTAX  SEQUENCE OF OnuWifiConfigChannelEntry
                 ACCESS  not-accessible
                 STATUS  mandatory
                 DESCRIPTION
                          "ONU Wifi channel config table."
                 ::= { nmsGponWifiPortObj 2 }

             onuWifiConfigChannelEntry OBJECT-TYPE
                 SYNTAX OnuWifiConfigChannelEntry
                 ACCESS  not-accessible
                 STATUS  mandatory
                 DESCRIPTION
                          "ONU Wifi channel config table entry."
                 INDEX { onuWifiConfigChannelDeviceIndex,  onuWifiConfigChannelPortIndex}
             ::= { onuWifiConfigChannelTable 1 }

             OnuWifiConfigChannelEntry ::=
                 SEQUENCE {
                     onuWifiConfigChannelDeviceIndex
                         INTEGER,
                     onuWifiConfigChannelPortIndex 
                         INTEGER,
                     onuWifiConfigChannelWidth
                         INTEGER,
                     onuWifiConfigChannelId
                         INTEGER,
                     onuWifiConfigChannelRowStatus
                         RowStatus               
                 }

              onuWifiConfigChannelDeviceIndex OBJECT-TYPE
                  SYNTAX  INTEGER
                  ACCESS  read-only
                  STATUS  mandatory
                  DESCRIPTION
                          "Index of the table, ONU port index."
                  ::= { onuWifiConfigChannelEntry 1 }
                     
              onuWifiConfigChannelPortIndex OBJECT-TYPE
                  SYNTAX  INTEGER{
                            w_2_4_G_mode(1),
                            w_5G_mode(2)
                            }     
                  ACCESS  read-only
                  STATUS  mandatory
                  DESCRIPTION
                          "Index of the table, ONU wifi 2.4G(1)/5G(2) mode index. "
                  ::= { onuWifiConfigChannelEntry 2 }
                     
              onuWifiConfigChannelWidth OBJECT-TYPE
                  SYNTAX  INTEGER{
                            w_20MHz(1),
                            w_40MHz(2)
                            w_20_40MHz(3),
                            w_80MHz(4)
                            }     
                  ACCESS  read-write
                  STATUS  mandatory
                  DESCRIPTION
                          "Wifi Channel Width:
                                1--20MHz for 2.4G/5G
                                2--40MHz for 2.4G/5G
                                3--20/40MHz for 2.4G
                                4--80MHz for 5G"
                  ::= { onuWifiConfigChannelEntry 3 } 
                  
              onuWifiConfigChannelId OBJECT-TYPE
                  SYNTAX  INTEGER
                  ACCESS  read-write
                  STATUS  mandatory
                  DESCRIPTION
                          "Wifi Channel Id:
                            Id:0      for auto choose channel id
                            Id:1-13   for 20MHz width for 2.4G
                            Id:5-13   for 40MHz or 20/40MHz width 2.4G
                            Id:36\40\44\48\52\56\60\64\149\153\157\161\165 for 5G 
                            And id 165 is only for 20Mhz(5G) channel width"
                  ::= { onuWifiConfigChannelEntry 4 }
            
               onuWifiConfigChannelRowStatus OBJECT-TYPE
                  SYNTAX  RowStatus
                  ACCESS  read-create
                  STATUS  mandatory
                  DESCRIPTION
                          ""
                  ::= { onuWifiConfigChannelEntry 5 } 
              
--Wifi ssid 配置
             onuWifiConfigSsidTable OBJECT-TYPE
                 SYNTAX  SEQUENCE OF OnuWifiConfigSsidEntry
                 ACCESS  not-accessible
                 STATUS  mandatory
                 DESCRIPTION
                          "ONU Wifi ssid port config table."
                 ::= { nmsGponWifiPortObj 3 }
             onuWifiConfigSsidEntry OBJECT-TYPE
                 SYNTAX OnuWifiConfigSsidEntry
                 ACCESS  not-accessible
                 STATUS  mandatory
                 DESCRIPTION
                          "ONU Wifi ssid config table entry."
                 INDEX { onuWifiConfigSsidDeviceIndex,  onuWifiConfigSsidPortIndex}
             ::= { onuWifiConfigSsidTable 1 }
             
             OnuWifiConfigSsidEntry ::=
                 SEQUENCE {
                     onuWifiConfigSsidDeviceIndex
                         INTEGER,
                     onuWifiConfigSsidPortIndex 
                         INTEGER,
                     onuWifiConfigSsidAdmin
                         INTEGER,
                     onuWifiConfigSsidbroadcastadmin
                         INTEGER,
                     onuWifiConfigSsidMaxsta 
                         INTEGER,
                     onuWifiConfigWlanStandard
                         INTEGER,
                     onuWifiConfigSGI
                         INTEGER,
                     onuWifiConfigSsidRowStatus
                         RowStatus               
                 }

          onuWifiConfigSsidDeviceIndex OBJECT-TYPE
              SYNTAX  INTEGER
              ACCESS  read-only
              STATUS  mandatory
              DESCRIPTION
                      "Index of the table, ONU port index."
              ::= { onuWifiConfigSsidEntry 1 }
                 
          onuWifiConfigSsidPortIndex OBJECT-TYPE
              SYNTAX  INTEGER
              ACCESS  read-only
              STATUS  mandatory
              DESCRIPTION
                      "Index of the table, ssid index "
              ::= { onuWifiConfigSsidEntry 2 }
              
          onuWifiConfigSsidAdmin OBJECT-TYPE
              SYNTAX  INTEGER{
                        enable(1),
                        disable(2)
                        }                    
              ACCESS  read-write
              STATUS  mandatory
              DESCRIPTION
                      "Ssid Admin:
                       1-Eable;2-Disable"
              ::= { onuWifiConfigSsidEntry 3 }
                 
          onuWifiConfigSsidbroadcastadmin OBJECT-TYPE
              SYNTAX  INTEGER{
                        enable(1),
                        disable(2)
                        }      
              ACCESS  read-write
              STATUS  mandatory
              DESCRIPTION
                      "Ssid Broadcast Admin:
                       1-Eable;2-Disable"
              ::= { onuWifiConfigSsidEntry 4 } 
              
          onuWifiConfigSsidMaxsta OBJECT-TYPE
              SYNTAX  INTEGER
              ACCESS  read-write
              STATUS  mandatory
              DESCRIPTION
                      "1-128 config ssid max user number, 
                       0-- max user number is not limited"
              ::= { onuWifiConfigSsidEntry 5 }
                 
          onuWifiConfigWlanStandard OBJECT-TYPE
              SYNTAX  INTEGER
              ACCESS  read-write
              STATUS  mandatory
              DESCRIPTION
                      "WlanStandard:
                      1--802.11b(2.4G)
                      2--802.11g(2.4G)
                      3--802.11n(2.4G)
                      4--802.11b+802.11g(2.4G)
                      5--802.11g+802.11n(2.4G)
                      6--802.11b+802.11g+802.11n(2.4G)
                      7--A(5G)
                      8--N(5G)
                      9--A+N(5G)
                      10--AC(5G)
                      11--N+AC(5G)
                      12--A+N+AC(5G)"
              ::= { onuWifiConfigSsidEntry 6 }
              
          onuWifiConfigSGI OBJECT-TYPE
              SYNTAX  INTEGER{
                        enable(1),
                        disable(2)
                        }               
              ACCESS  read-write
              STATUS  mandatory
              DESCRIPTION
                      "SGI:
                       1-Eable;2-Disable"
              ::= { onuWifiConfigSsidEntry 7 }
              
          onuWifiConfigSsidRowStatus OBJECT-TYPE
              SYNTAX  RowStatus
              ACCESS  read-create
              STATUS  mandatory
              DESCRIPTION
                      ""
              ::= { onuWifiConfigSsidEntry 8 } 


--Wifi加密配置

             onuWifiConfigSsidEncryptTable OBJECT-TYPE
                 SYNTAX  SEQUENCE OF OnuWifiConfigSsidEncryptEntry
                 ACCESS  not-accessible
                 STATUS  mandatory
                 DESCRIPTION
                          "ONU Wifi encrypt config table."
                 ::= { nmsGponWifiPortObj 4 }

             onuWifiConfigSsidEncryptEntry OBJECT-TYPE
                 SYNTAX OnuWifiConfigSsidEncryptEntry
                 ACCESS  not-accessible
                 STATUS  mandatory
                 DESCRIPTION
                          "ONU Wifi encrypt config table entry."
                 INDEX { onuWifiConfigSsidEncryptDeviceIndex,  onuWifiConfigSsidEncryptPortIndex}
             ::= { onuWifiConfigSsidEncryptTable 1 }

             OnuWifiConfigSsidEncryptEntry ::=
                 SEQUENCE {
                     onuWifiConfigSsidEncryptDeviceIndex
                         INTEGER,
                     onuWifiConfigSsidEncryptPortIndex 
                         INTEGER,
                     onuWifiConfigSsidEncryptMode
                         INTEGER,
                     onuWifiConfigSsidEncryptKey
                         OCTET STRING,
                     onuWifiConfigSsidEncryptRowStatus
                         RowStatus               
                 }       

          onuWifiConfigSsidEncryptDeviceIndex OBJECT-TYPE
              SYNTAX  INTEGER
              ACCESS  read-only
              STATUS  mandatory
              DESCRIPTION
                      "Index of the table, ONU port index."
              ::= { onuWifiConfigSsidEncryptEntry 1 }
                 
          onuWifiConfigSsidEncryptPortIndex OBJECT-TYPE
              SYNTAX  INTEGER
              ACCESS  read-only
              STATUS  mandatory
              DESCRIPTION
                      "Index of the table, wifi ssid index "
              ::= { onuWifiConfigSsidEncryptEntry 2 }
              
          onuWifiConfigSsidEncryptMode OBJECT-TYPE
              SYNTAX  INTEGER{
                        none(0),
                        wep(1),
                        wpa(2),
                        wpa2(3),
                        wpa_wpa2(4)
                        }               
              ACCESS  read-write
              STATUS  mandatory
              DESCRIPTION
                      "Encrypt Mode:
                       0--none
                       1--wep
                       2--wpa
                       3--wpa2
                       4--wpa_wpa2"
              ::= { onuWifiConfigSsidEncryptEntry 3 }
                 
          onuWifiConfigSsidEncryptKey OBJECT-TYPE
              SYNTAX  OCTET STRING
              ACCESS  read-write
              STATUS  mandatory
              DESCRIPTION
                      "wifi encrypt key (8-64 byte)"
              ::= { onuWifiConfigSsidEncryptEntry 4 } 

          onuWifiConfigSsidEncryptRowStatus OBJECT-TYPE
              SYNTAX  RowStatus
              ACCESS  read-create
              STATUS  mandatory
              DESCRIPTION
                      ""
              ::= { onuWifiConfigSsidEncryptEntry 5} 


--Wifi ssid name配置

             onuWifiConfigSsidNameTable OBJECT-TYPE
                 SYNTAX  SEQUENCE OF OnuWifiConfigSsidNameEntry
                 ACCESS  not-accessible
                 STATUS  mandatory
                 DESCRIPTION
                          "ONU Wifi config ssid name table."
                 ::= { nmsGponWifiPortObj 5 }

             onuWifiConfigSsidNameEntry OBJECT-TYPE
                 SYNTAX OnuWifiConfigSsidNameEntry
                 ACCESS  not-accessible
                 STATUS  mandatory
                 DESCRIPTION
                          "ONU Wifi config ssid name table entry."
                 INDEX { onuWifiConfigSsidNameDeviceIndex,  onuWifiConfigSsidNamePortIndex}
             ::= { onuWifiConfigSsidNameTable 1 }

             OnuWifiConfigSsidNameEntry ::=
                 SEQUENCE {
                     onuWifiConfigSsidNameDeviceIndex
                         INTEGER,
                     onuWifiConfigSsidNamePortIndex 
                         INTEGER,
                     onuWifiConfigSsidName
                         OCTET STRING,
                     onuWifiConfigSsidNameRowStatus
                         RowStatus               
                 }

          onuWifiConfigSsidNameDeviceIndex OBJECT-TYPE
              SYNTAX  INTEGER
              ACCESS  read-only
              STATUS  mandatory
              DESCRIPTION
                      "Index of the table, ONU port index."
              ::= { onuWifiConfigSsidNameEntry 1 }
                 
          onuWifiConfigSsidNamePortIndex OBJECT-TYPE
              SYNTAX  INTEGER
              ACCESS  read-only
              STATUS  mandatory
              DESCRIPTION
                      "Index of the table, wifi ssid index "
              ::= { onuWifiConfigSsidNameEntry 2 }
              
          onuWifiConfigSsidName OBJECT-TYPE
              SYNTAX  OCTET STRING           
              ACCESS  read-write
              STATUS  mandatory
              DESCRIPTION
                      "config ssid name (1-32 byte) "
              ::= { onuWifiConfigSsidNameEntry 3 }
                 
          onuWifiConfigSsidNameRowStatus OBJECT-TYPE
              SYNTAX  RowStatus
              ACCESS  read-create
              STATUS  mandatory
              DESCRIPTION
                      ""
              ::= { onuWifiConfigSsidNameEntry 4 } 


--nmsGponMacSearchObj MAC信息 OID:1.3.6.1.4.1.3320.10.15
nmsGponMacSearchObj   OBJECT IDENTIFIER ::= { nmsGponMIB 15 }

         gponMacSearchResultTable OBJECT-TYPE
             SYNTAX SEQUENCE OF GponMacSearchResultEntry
             ACCESS not-accessible
             STATUS  mandatory
             DESCRIPTION
                     "A list of search result."
             ::= { nmsGponMacSearchObj 1 }

         gponMacSearchResultEntry OBJECT-TYPE
             SYNTAX  GponMacSearchResultEntry
             ACCESS  not-accessible
             STATUS  mandatory
             DESCRIPTION
                     "An entry of search result."
             INDEX { gponMacSearchResultIndex }
             ::= { gponMacSearchResultTable 1 }
               
         GponMacSearchResultEntry ::=
             SEQUENCE {
                 gponMacSearchResultIndex
                     INTEGER,
                 gponMacSearchResultIf
                     INTEGER,
                 gponMacSearchResultVp
                     INTEGER,
                 gponMacSearchResultVlan
                     INTEGER,
                 gponMacSearchResultMacAddress
                     MacAddress
             }

         gponMacSearchResultIndex OBJECT-TYPE
             SYNTAX  INTEGER
             ACCESS  read-only
             STATUS  mandatory
             DESCRIPTION
                 "Entry index for search result."
            ::= { gponMacSearchResultEntry 1 }

         gponMacSearchResultIf OBJECT-TYPE
             SYNTAX  INTEGER
             ACCESS  read-only
             STATUS  mandatory
             DESCRIPTION
                 "Diid of mac entry."
            ::= { gponMacSearchResultEntry 2 }
                
         gponMacSearchResultVp OBJECT-TYPE
             SYNTAX  INTEGER
             ACCESS  read-only
             STATUS  mandatory
             DESCRIPTION
                 "Virtual port of mac entry"
            ::= { gponMacSearchResultEntry 3 }
            
         gponMacSearchResultVlan OBJECT-TYPE
             SYNTAX  INTEGER
             ACCESS  read-only
             STATUS  mandatory
             DESCRIPTION
                 "Vlan of mac entry."
            ::= { gponMacSearchResultEntry 4 }

         gponMacSearchResultMacAddress OBJECT-TYPE
             SYNTAX  MacAddress
             ACCESS  read-only
             STATUS  mandatory
             DESCRIPTION
                 "Mac address of mac entry."
            ::= { gponMacSearchResultEntry 5 }

         gponMacSearchType OBJECT-TYPE
             SYNTAX INTEGER { mac(1), mac-vid(2), if-index(3), vid(4) }
             ACCESS read-write
             STATUS current
             DESCRIPTION
                     "MAC address search type. Set this OID will trigger the search action. "
             ::= { nmsGponMacSearchObj 2 }

         gponMacSearchTime OBJECT-TYPE
             SYNTAX DateAndTime
             MAX-ACCESS read-only
             STATUS current
             DESCRIPTION
                     "The date time corresponding to current gponMacSearchResultTable."
             ::= { nmsGponMacSearchObj 3 }

         gponMacSearchCondMac OBJECT-TYPE
             SYNTAX MacAddress
             ACCESS read-write
             STATUS current
             DESCRIPTION
                     "MAC address condition for search. Get will return the MAC corresponding to current gponMacSearchResultTable, 00:00:00:00:00:00 for not used."
             ::= { nmsGponMacSearchObj 4 }
                    
         gponMacSearchCondVid OBJECT-TYPE
             SYNTAX INTEGER
             ACCESS read-write
             STATUS current
             DESCRIPTION
                     "Vlan id condition for search. Get will return the vlan id corresponding to current gponMacSearchResultTable, 0 for not used."
             ::= { nmsGponMacSearchObj 5 }

         gponMacSearchCondIfIndex OBJECT-TYPE
             SYNTAX INTEGER
             ACCESS read-write
             STATUS current
             DESCRIPTION
                     "IfIndex condition for search. Get will return the IfIndex corresponding to current gponMacSearchResultTable, 0 for not used."
             ::= { nmsGponMacSearchObj 6 }


--nmsGponUNIPortObj UNI端口任务 OID:1.3.6.1.4.1.3320.10.16

nmsGponOnuTypeTemplateObj   OBJECT IDENTIFIER ::= { nmsGponMIB 16 }  

-- ONU类型模版配置表

             gponOnuTypeTemplateTable OBJECT-TYPE
                 SYNTAX  SEQUENCE OF GponOnuTypeTemplateEntry
                 ACCESS  not-accessible
                 STATUS  mandatory
                 DESCRIPTION
                          "Onu type template information config table."
                 ::= { nmsGponOnuTypeTemplateObj 1 }

             gponOnuTypeTemplateEntry OBJECT-TYPE
                 SYNTAX GponOnuTypeTemplateEntry
                 ACCESS  not-accessible
                 STATUS  mandatory
                 DESCRIPTION
                          "Onu type template information config table entry."
                 INDEX { gponOnuTypeTemplateIndex }
             ::= { gponOnuTypeTemplateTable 1 }

             GponOnuTypeTemplateEntry ::=
                 SEQUENCE {
                     gponOnuTypeTemplateIndex
                         INTEGER,
                     gponOnuTypeTemplateName
                         OCTET STRING, 
                     gponOnuTypeTemplateMatchMask
                         BITS,
                     gponOnuTypeTemplateVenderID
                         OCTET STRING,
                     gponOnuTypeTemplateEquipmentID
                         OCTET STRING,
                     gponOnuTypeTemplateCtcOnuType
                         INTEGER,
                     gponOnuTypeTemplateTotalEthUNINumber
                         INTEGER,
                     gponOnuTypeTemplateTotalVEIPNumber
                         INTEGER,
                     gponOnuTypeTemplateRowStatus
                         RowStatus,
                     gponOnuTypeTemplateTotalVOIPNumber
                         INTEGER,
                     gponOnuTypeTemplateTotalIPHostNumber
                         INTEGER,
                     gponOnuTypeTemplateTotalOtherUniNumber
                         INTEGER,
                     gponOnuTypeTemplateTotalGeneralUniNumber
                         INTEGER
            }
                 
          gponOnuTypeTemplateIndex OBJECT-TYPE
              SYNTAX  INTEGER
              ACCESS  read-only
              STATUS  mandatory

              DESCRIPTION
                      ""
              ::= { gponOnuTypeTemplateEntry 1 }


          gponOnuTypeTemplateName OBJECT-TYPE
              SYNTAX  OCTET STRING
              ACCESS  read-write
              STATUS  mandatory

              DESCRIPTION
                      ""
              ::= { gponOnuTypeTemplateEntry 2 }
              
          gponOnuTypeTemplateMatchMask OBJECT-TYPE
              SYNTAX  BITS{
                        venderID(0),
                        ctcOnuType(1),
                        ethUniNumber(2),
                        veipUniNumber(3),
                        voipUniNumber(4),
                        ipHostNumber(5),
                        otherUniNumber(6),
                        generalUniNumber(7)
                        }
              ACCESS  read-write
              STATUS  mandatory

              DESCRIPTION
                      "Match mask for onutype template."
              ::= { gponOnuTypeTemplateEntry 3 }

          gponOnuTypeTemplateVenderID OBJECT-TYPE
              SYNTAX  OCTET STRING
              ACCESS  read-write
              STATUS  mandatory

              DESCRIPTION
                      ""
              ::= { gponOnuTypeTemplateEntry 4 }

          gponOnuTypeTemplateEquipmentID OBJECT-TYPE
              SYNTAX  OCTET STRING
              ACCESS  read-write
              STATUS  mandatory

              DESCRIPTION
                      ""
              ::= { gponOnuTypeTemplateEntry 5 }

          gponOnuTypeTemplateCtcOnuType OBJECT-TYPE
              SYNTAX  INTEGER{
                        sfu(0),
                        hgu(1),
                        sbu(2),
                        cbu(3),
                        mdu(4),
                        mtu(5)
                        }
              ACCESS  read-write
              STATUS  mandatory

              DESCRIPTION
                      "ONU type match information. 0--SFU, 1--HGU, 2--SBU, 3--CBU, 4--MDU, 5--MTU."
              ::= { gponOnuTypeTemplateEntry 6 }
           
           gponOnuTypeTemplateTotalEthUNINumber OBJECT-TYPE
              SYNTAX  INTEGER(0..32)
              ACCESS  read-write
              STATUS  mandatory

              DESCRIPTION
                      "Total ethernet UNI port number to match, 0-32."
              ::= { gponOnuTypeTemplateEntry 7 }

           gponOnuTypeTemplateTotalVEIPNumber OBJECT-TYPE
              SYNTAX  INTEGER(0..4)
              ACCESS  read-write
              STATUS  mandatory

              DESCRIPTION
                      "Total VEIP UNI port number to match, 0-4."
              ::= { gponOnuTypeTemplateEntry 8 }

           gponOnuTypeTemplateRowStatus OBJECT-TYPE
              SYNTAX  RowStatus
              ACCESS  read-create
              STATUS  mandatory

              DESCRIPTION
                      ""
              ::= { gponOnuTypeTemplateEntry 9 }

           gponOnuTypeTemplateTotalVOIPNumber OBJECT-TYPE
              SYNTAX  INTEGER(0..16)
              ACCESS  read-write
              STATUS  mandatory

              DESCRIPTION
                      "Total VOIP UNI port number to match, 0-16."
              ::= { gponOnuTypeTemplateEntry 10 }

           gponOnuTypeTemplateTotalIPHostNumber OBJECT-TYPE
              SYNTAX  INTEGER(0..8)
              ACCESS  read-write
              STATUS  mandatory

              DESCRIPTION
                      "Total IP host port number to match, 0-8."
              ::= { gponOnuTypeTemplateEntry 11 }

           gponOnuTypeTemplateTotalOtherUniNumber OBJECT-TYPE
              SYNTAX  INTEGER(0..96)
              ACCESS  read-write
              STATUS  mandatory

              DESCRIPTION
                      "Total other UNI port number to match, 0-96."
              ::= { gponOnuTypeTemplateEntry 12 }

           gponOnuTypeTemplateTotalGeneralUniNumber OBJECT-TYPE
              SYNTAX  INTEGER(0..96)
              ACCESS  read-write
              STATUS  mandatory

              DESCRIPTION
                      "Total general UNI port number to match, 0-96."
              ::= { gponOnuTypeTemplateEntry 13 }

--gponOnuTypeTemplateOnuConfigTable  OID:1.3.6.1.4.1.3320.10.16.2

             gponOnuTypeTemplateOnuConfigTable OBJECT-TYPE
                 SYNTAX  SEQUENCE OF GponOnuTypeTemplateOnuConfigEntry
                 ACCESS  not-accessible
                 STATUS  mandatory
                 DESCRIPTION
                          "gpon onu type template onu configuration table."
                 ::= { nmsGponOnuTypeTemplateObj 2 }

             gponOnuTypeTemplateOnuConfigEntry OBJECT-TYPE
                 SYNTAX GponOnuTypeTemplateOnuConfigEntry
                 ACCESS  not-accessible
                 STATUS  mandatory
                 DESCRIPTION
                          "gpon onu type template onu configuration entry ."
                 INDEX { gponOnuTypeTemplateOnuConfigTemplateIndex }
             ::= { gponOnuTypeTemplateOnuConfigTable 1 }

             GponOnuTypeTemplateOnuConfigEntry ::=
                 SEQUENCE {
                     gponOnuTypeTemplateOnuConfigTemplateIndex
                         INTEGER,
                      gponOnuTypeTemplateOnuConfigEnablePM 
                         INTEGER,
                      gponOnuTypeTemplateOnuConfigFlowProfileID 
                         INTEGER,
                      gponOnuTypeTemplateOnuConfigTcontVirPortBindingProfileID 
                         INTEGER,
                      gponOnuTypeTemplateOnuConfigOnuProfileID 
                         INTEGER,
                     gponOnuTypeTemplateOnuConfigUsMapProfileID 
                         INTEGER,
                     gponOnuTypeTemplateOnuConfigOpticalProfileID 
                         INTEGER,
                     gponOnuTypeTemplateOnuConfigFEC 
                         INTEGER, 
                     gponOnuTypeTemplateOnuConfigLoopbackDetectProtocol 
                         INTEGER,
                     gponOnuTypeTemplateOnuConfigLoopbackDetectProfileID 
                         INTEGER,
                     gponOnuTypeTemplateOnuConfigCatvProtocol 
                         INTEGER,
                     gponOnuTypeTemplatePoePowerLimit
                         INTEGER, 
                     gponOnuTypeTemplateOnuConfigDescription
                         OCTET STRING,
                     gponOnuTypeTemplateOnuConfigAlwaysCheckTemplate
                         INTEGER,
                     gponOnuTypeTemplateOnuConfigUpstreamMacSecurity 
                         INTEGER,
                     gponOnuTypeTemplateOnuConfigRemoteAccessTelnet
                         INTEGER, 
                     gponOnuTypeTemplateOnuConfigRemoteAccessPing
                         INTEGER, 
                     gponOnuTypeTemplateOnuConfigRemoteAccessWebui
                         INTEGER,      
                     gponOnuTypeTemplateOnuConfigPoeProtocol
                         INTEGER,
                     gponOnuTypeTemplateOnuConfigSnmpProfileID 
                         INTEGER,
                     gponOnuTypeTemplateOnuConfigVoiceVlanProfileID 
                         INTEGER,
                     gponOnuTypeTemplateOnuConfigDot1xProfileID 
                         INTEGER
                 }
                 
          gponOnuTypeTemplateOnuConfigTemplateIndex OBJECT-TYPE
              SYNTAX  INTEGER
              ACCESS  read-only
              STATUS  mandatory

              DESCRIPTION
                      "GPON ONU device configuration index."
              ::= { gponOnuTypeTemplateOnuConfigEntry 1 }

          gponOnuTypeTemplateOnuConfigEnablePM OBJECT-TYPE
              SYNTAX  INTEGER{
                               enable(1),
                               disable(2)
                              }
              ACCESS  read-write
              STATUS  mandatory

              DESCRIPTION
                      ""
              ::= { gponOnuTypeTemplateOnuConfigEntry 2 }

          gponOnuTypeTemplateOnuConfigFlowProfileID OBJECT-TYPE
              SYNTAX  INTEGER
              ACCESS  read-write
              STATUS  mandatory

              DESCRIPTION
                      "The profileIndex corresponding to ONU Flow Profile Table. 0 means invalid. Default value is 1."
              ::= { gponOnuTypeTemplateOnuConfigEntry 3 }

          gponOnuTypeTemplateOnuConfigTcontVirPortBindingProfileID OBJECT-TYPE
              SYNTAX  INTEGER
              ACCESS  read-write
              STATUS  mandatory

              DESCRIPTION
                      "It points to the associated T-CONT and virtual port binding profile index. 0 means invalid."
              ::= { gponOnuTypeTemplateOnuConfigEntry 4 }

          gponOnuTypeTemplateOnuConfigOnuProfileID OBJECT-TYPE
              SYNTAX  INTEGER
              ACCESS  read-write
              STATUS  mandatory

              DESCRIPTION
                      ""
              ::= { gponOnuTypeTemplateOnuConfigEntry 5 }

          gponOnuTypeTemplateOnuConfigUsMapProfileID OBJECT-TYPE
              SYNTAX  INTEGER
              ACCESS  read-write
              STATUS  mandatory

              DESCRIPTION
                      ""
              ::= { gponOnuTypeTemplateOnuConfigEntry 6 }

          gponOnuTypeTemplateOnuConfigOpticalProfileID OBJECT-TYPE
              SYNTAX  INTEGER
              ACCESS  read-write
              STATUS  mandatory

              DESCRIPTION
                      "The profileIndex corresponding to ONU Optical alarm Profile Table. 0 means invalid."
              ::= { gponOnuTypeTemplateOnuConfigEntry 7 }
          
          gponOnuTypeTemplateOnuConfigFEC OBJECT-TYPE
              SYNTAX  INTEGER{
                               enable(1),
                               disable(2)
                              }
              ACCESS  read-write
              STATUS  mandatory

              DESCRIPTION
                      "For ONU FEC config"
              ::= { gponOnuTypeTemplateOnuConfigEntry 8 }
          gponOnuTypeTemplateOnuConfigLoopbackDetectProtocol OBJECT-TYPE
              SYNTAX  INTEGER{
                               ctc(0),
                               private(1)
                              }
              ACCESS  read-write
              STATUS  mandatory

              DESCRIPTION
                      "0-CTC；1-Private"
              ::= { gponOnuTypeTemplateOnuConfigEntry 9 }
          gponOnuTypeTemplateOnuConfigLoopbackDetectProfileID OBJECT-TYPE
              SYNTAX  INTEGER
              ACCESS  read-write
              STATUS  mandatory

              DESCRIPTION
                      "The profileIndex corresponding to ONU loopback detection Profile Table. 0 means invalid."
              ::= { gponOnuTypeTemplateOnuConfigEntry 10 }

          gponOnuTypeTemplateOnuConfigCatvProtocol OBJECT-TYPE
              SYNTAX  INTEGER{
                               itu(0),
                               private(1)
                              }
              ACCESS  read-write
              STATUS  mandatory

              DESCRIPTION
                      "0-ITU；1-Private"
              ::= { gponOnuTypeTemplateOnuConfigEntry 11 }
          gponOnuTypeTemplatePoePowerLimit OBJECT-TYPE
              SYNTAX  INTEGER
              ACCESS  read-write
              STATUS  mandatory

              DESCRIPTION
                      ""
              ::= { gponOnuTypeTemplateOnuConfigEntry 12 }  
          gponOnuTypeTemplateOnuConfigDescription OBJECT-TYPE
              SYNTAX  OCTET STRING
              ACCESS  read-write
              STATUS  mandatory

              DESCRIPTION
                      "The ONU description information"
              ::= { gponOnuTypeTemplateOnuConfigEntry 13 }
              
          gponOnuTypeTemplateOnuConfigAlwaysCheckTemplate OBJECT-TYPE
              SYNTAX  INTEGER{
                               force-on(1),
                               force-off(2)
                              }
              ACCESS  read-write
              STATUS  mandatory

              DESCRIPTION
                      "ONU alway check and config the onutype template, 1--forceon, 2--forceoff."
              ::= { gponOnuTypeTemplateOnuConfigEntry 14 }
          gponOnuTypeTemplateOnuConfigUpstreamMacSecurity OBJECT-TYPE
              SYNTAX  INTEGER{
                               noconfig(0),
                               enable(1),
                               disable(2)
                              }
              ACCESS  read-write
              STATUS  mandatory

              DESCRIPTION
                      "Forbid onu uni-side learned mac move to pon-side"
              ::= { gponOnuTypeTemplateOnuConfigEntry 15 }
          gponOnuTypeTemplateOnuConfigRemoteAccessTelnet OBJECT-TYPE
              SYNTAX  INTEGER{
                               noconfig(0),
                               enable(1),
                               disable(2)
                              }
              ACCESS  read-write
              STATUS  mandatory

              DESCRIPTION
                      "Permit telnet onu from pon-side"
              ::= { gponOnuTypeTemplateOnuConfigEntry 16 }
          gponOnuTypeTemplateOnuConfigRemoteAccessPing OBJECT-TYPE
              SYNTAX  INTEGER{
                               noconfig(0),
                               enable(1),
                               disable(2)
                              }
              ACCESS  read-write
              STATUS  mandatory

              DESCRIPTION
                      "Permit ping onu from pon-side"
              ::= { gponOnuTypeTemplateOnuConfigEntry 17 }
          gponOnuTypeTemplateOnuConfigRemoteAccessWebui OBJECT-TYPE
              SYNTAX  INTEGER{
                               noconfig(0),
                               enable(1),
                               disable(2)
                              }
              ACCESS  read-write
              STATUS  mandatory

              DESCRIPTION
                      "Permit access onu webUI from pon-side"
              ::= { gponOnuTypeTemplateOnuConfigEntry 18 } 
              
          gponOnuTypeTemplateOnuConfigPoeProtocol OBJECT-TYPE
              SYNTAX  INTEGER{
                                itu(0),
                                private(1)
                             }
              ACCESS  read-write
              STATUS  mandatory

              DESCRIPTION
                      "Poe protocol."
              ::= { gponOnuTypeTemplateOnuConfigEntry 19 }

          gponOnuTypeTemplateOnuConfigSnmpProfileID OBJECT-TYPE
              SYNTAX  INTEGER
              ACCESS  read-write
              STATUS  mandatory
              
              DESCRIPTION
                      "The profileIndex corresponding to ONU SNMP Profile Table. 0 means invalid."
              ::= { gponOnuTypeTemplateOnuConfigEntry 20 }

          gponOnuTypeTemplateOnuConfigVoiceVlanProfileID OBJECT-TYPE
              SYNTAX  INTEGER
              ACCESS  read-write
              STATUS  mandatory
              
              DESCRIPTION
                      "The profileIndex corresponding to ONU Voice-VLAN Profile Table. 0 means invalid."
              ::= { gponOnuTypeTemplateOnuConfigEntry 21 }

          gponOnuTypeTemplateOnuConfigDot1xProfileID OBJECT-TYPE
              SYNTAX  INTEGER
              ACCESS  read-write
              STATUS  mandatory
              
              DESCRIPTION
                      "The profileIndex corresponding to ONU 802.1x Profile Table. 0 means invalid."
              ::= { gponOnuTypeTemplateOnuConfigEntry 22 }

           
-- ONU类型模版UNI端口配置表

             onuTypeTemplateUniPortConfigTable OBJECT-TYPE
                 SYNTAX  SEQUENCE OF OnuTypeTemplateUniPortConfigEntry
                 ACCESS  not-accessible
                 STATUS  mandatory
                 DESCRIPTION
                          "Onu type template UNI port config table."
                 ::= { nmsGponOnuTypeTemplateObj 3 }

             onuTypeTemplateUniPortConfigEntry OBJECT-TYPE
                 SYNTAX OnuTypeTemplateUniPortConfigEntry
                 ACCESS  not-accessible
                 STATUS  mandatory
                 DESCRIPTION
                          "Onu type template UNI port config table entry."
                 INDEX { onuTypeTemplateUniPortConfigTemplateIndex, onuTypeTemplateUniPortConfigPortIndex }
             ::= { onuTypeTemplateUniPortConfigTable 1 }

             OnuTypeTemplateUniPortConfigEntry ::=
                 SEQUENCE {
                     onuTypeTemplateUniPortConfigTemplateIndex
                         INTEGER,
                     onuTypeTemplateUniPortConfigPortIndex
                         INTEGER,
                     onuTypeTemplateUniPortConfigEthernetProfileID
                         INTEGER,
                     onuTypeTemplateUniPortConfigLoopbackDetect
                         INTEGER,
                     onuTypeTemplateUniPortConfigPoeAFATmode
                         INTEGER,
                     onuTypeTemplateUniPortConfigPoeWorkMode
                         INTEGER,
                     onuTypeTemplateUniPortConfigRowStatus
                         RowStatus,
            }
                 
                 
          onuTypeTemplateUniPortConfigTemplateIndex OBJECT-TYPE
              SYNTAX  INTEGER
              ACCESS  read-only
              STATUS  mandatory

              DESCRIPTION
                      ""
              ::= { onuTypeTemplateUniPortConfigEntry 1 }


          onuTypeTemplateUniPortConfigPortIndex OBJECT-TYPE
              SYNTAX  INTEGER
              ACCESS  read-only
              STATUS  mandatory

              DESCRIPTION
                      ""
              ::= { onuTypeTemplateUniPortConfigEntry 2 }

          onuTypeTemplateUniPortConfigEthernetProfileID OBJECT-TYPE
              SYNTAX  INTEGER
              ACCESS  read-write
              STATUS  mandatory

              DESCRIPTION
                      "It points to the associated Ethernet UNI profile. 0 means cancel profile config. 
                      Default value is 0."
              ::= { onuTypeTemplateUniPortConfigEntry 3 }

          onuTypeTemplateUniPortConfigLoopbackDetect OBJECT-TYPE
              SYNTAX  INTEGER{
                                enable(1),
                                disable(2)
                              }
              ACCESS  read-write
              STATUS  mandatory

              DESCRIPTION
                      "1-enable 2-disable "
              ::= { onuTypeTemplateUniPortConfigEntry 4 }

          onuTypeTemplateUniPortConfigPoeAFATmode OBJECT-TYPE
              SYNTAX  INTEGER{
                        af(1),
                        at(2)
                        }
              ACCESS  read-write
              STATUS  mandatory

              DESCRIPTION
                      "1-AF 2-AT"

              ::= { onuTypeTemplateUniPortConfigEntry 5 }
           
           onuTypeTemplateUniPortConfigPoeWorkMode OBJECT-TYPE
              SYNTAX  INTEGER{
                        disable(1),
                        normal(2),
                        force-on(3)
                        }
              ACCESS  read-write
              STATUS  mandatory

              DESCRIPTION
                      "1-disable 2-normal 3-force-on"

              ::= { onuTypeTemplateUniPortConfigEntry 6 }

           onuTypeTemplateUniPortConfigRowStatus OBJECT-TYPE
              SYNTAX  RowStatus
              ACCESS  read-create
              STATUS  mandatory

              DESCRIPTION
                      ""
              ::= { onuTypeTemplateUniPortConfigEntry 7 }

-- ONU类型模版UNI/VEIP/Ip-Host端口通用配置表

             onuTypeTemplateCommonPortConfigTable OBJECT-TYPE
                 SYNTAX  SEQUENCE OF OnuTypeTemplateCommonPortConfigEntry
                 ACCESS  not-accessible
                 STATUS  mandatory
                 DESCRIPTION
                          "Onu type templae UNI port config table."
                 ::= { nmsGponOnuTypeTemplateObj 4 }

             onuTypeTemplateCommonPortConfigEntry OBJECT-TYPE
                 SYNTAX OnuTypeTemplateCommonPortConfigEntry
                 ACCESS  not-accessible
                 STATUS  mandatory
                 DESCRIPTION
                          "Onu type template UNI port config table entry."
                 INDEX { onuTypeTemplateCommonPortConfigTemplateIndex, onuTypeTemplateCommonPortConfigPortIndex }
             ::= { onuTypeTemplateCommonPortConfigTable 1 }

             OnuTypeTemplateCommonPortConfigEntry ::=
                 SEQUENCE {
                     onuTypeTemplateCommonPortConfigTemplateIndex
                         INTEGER,
                     onuTypeTemplateCommonPortConfigPortIndex
                         INTEGER,
                     onuTypeTemplateCommonPortConfigAdminState
                         INTEGER,
                     onuTypeTemplateCommonPortConfigOnuVLANTranslationProfileID
                         INTEGER,
                     onuTypeTemplateCommonPortConfigMcstOperProfileID
                         INTEGER,
                     onuTypeTemplateCommonPortConfigMcstStaticProfileID
                         INTEGER,
                     onuTypeTemplateCommonPortConfigMcstDynamicProfileID
                         INTEGER,
                     onuTypeTemplateCommonPortConfigRowStatus
                         RowStatus
            }
                 
                 
          onuTypeTemplateCommonPortConfigTemplateIndex OBJECT-TYPE
              SYNTAX  INTEGER
              ACCESS  read-only
              STATUS  mandatory

              DESCRIPTION
                      ""
              ::= { onuTypeTemplateCommonPortConfigEntry 1 }


          onuTypeTemplateCommonPortConfigPortIndex OBJECT-TYPE
              SYNTAX  INTEGER
              ACCESS  read-only
              STATUS  mandatory

              DESCRIPTION
                      ""
              ::= { onuTypeTemplateCommonPortConfigEntry 2 }

          onuTypeTemplateCommonPortConfigAdminState OBJECT-TYPE
              SYNTAX  INTEGER{
                               no-shutdown(1),
                               shutdown(2)
                             }
              ACCESS  read-write
              STATUS  mandatory

              DESCRIPTION
                      "1-No shutdown  2-Shutdown "
              ::= { onuTypeTemplateCommonPortConfigEntry 3 }

          onuTypeTemplateCommonPortConfigOnuVLANTranslationProfileID OBJECT-TYPE
              SYNTAX  INTEGER
              ACCESS  read-write
              STATUS  mandatory

              DESCRIPTION
                      "It stores the profileIndex of the associated ONU VLAN translation profile.0 means cancel
                       profile config. Default value is 0. "
              ::= { onuTypeTemplateCommonPortConfigEntry 4 }

          onuTypeTemplateCommonPortConfigMcstOperProfileID OBJECT-TYPE
              SYNTAX  INTEGER
              ACCESS  read-write
              STATUS  mandatory

              DESCRIPTION
                      "It points to the associated onu multicast operation configuration profile.
            0 means cancel profile config."
              ::= { onuTypeTemplateCommonPortConfigEntry 5 }

          onuTypeTemplateCommonPortConfigMcstStaticProfileID OBJECT-TYPE
              SYNTAX  INTEGER
              ACCESS  read-write
              STATUS  mandatory

              DESCRIPTION
                      "It points to the associated onu multicast static group configuration profile.
            0 means cancel profile config."
              ::= { onuTypeTemplateCommonPortConfigEntry 6 }

          onuTypeTemplateCommonPortConfigMcstDynamicProfileID OBJECT-TYPE
              SYNTAX  INTEGER
              ACCESS  read-write
              STATUS  mandatory

              DESCRIPTION
                      "It points to the associated onu multicast dynamic group configuration profile.
            0 means cancel profile config."

              ::= { onuTypeTemplateCommonPortConfigEntry 7 }
              
          onuTypeTemplateCommonPortConfigRowStatus OBJECT-TYPE
              SYNTAX  RowStatus
              ACCESS  read-create
              STATUS  mandatory

              DESCRIPTION
                      ""
              ::= { onuTypeTemplateCommonPortConfigEntry 8 }  

-- ONU类型模版VEIP端口配置表

             onuTypeTemplateVEIPPortConfigTable OBJECT-TYPE
                 SYNTAX  SEQUENCE OF OnuTypeTemplateVEIPPortConfigEntry
                 ACCESS  not-accessible
                 STATUS  mandatory
                 DESCRIPTION
                          "Onu type template VEIP port config table."
                 ::= { nmsGponOnuTypeTemplateObj 5 }

             onuTypeTemplateVEIPPortConfigEntry OBJECT-TYPE
                 SYNTAX OnuTypeTemplateVEIPPortConfigEntry
                 ACCESS  not-accessible
                 STATUS  mandatory
                 DESCRIPTION
                          "Onu type template VEIP port config table entry."
                 INDEX { onuTypeTemplateVEIPPortConfigTemplateIndex, onuTypeTemplateVEIPPortConfigPortIndex }
             ::= { onuTypeTemplateVEIPPortConfigTable 1 }

             OnuTypeTemplateVEIPPortConfigEntry ::=
                 SEQUENCE {
                     onuTypeTemplateVEIPPortConfigTemplateIndex
                         INTEGER,
                     onuTypeTemplateVEIPPortConfigPortIndex
                         INTEGER,
                     onuTypeTemplateVEIPPortConfigOnuVEIPProfileID
                         INTEGER,
                     onuTypeTemplateVEIPPortConfigRowStatus
                         RowStatus
            }
                 
                 
          onuTypeTemplateVEIPPortConfigTemplateIndex OBJECT-TYPE
              SYNTAX  INTEGER
              ACCESS  read-only
              STATUS  mandatory

              DESCRIPTION
                      ""
              ::= { onuTypeTemplateVEIPPortConfigEntry 1 }


          onuTypeTemplateVEIPPortConfigPortIndex OBJECT-TYPE
              SYNTAX  INTEGER
              ACCESS  read-only
              STATUS  mandatory

              DESCRIPTION
                      ""
              ::= { onuTypeTemplateVEIPPortConfigEntry 2 }

          onuTypeTemplateVEIPPortConfigOnuVEIPProfileID OBJECT-TYPE
              SYNTAX  INTEGER
              ACCESS  read-write
              STATUS  mandatory

              DESCRIPTION
                      "It points to the associated onu VEIP configuration profile.
            0 means cancel profile config."
              ::= { onuTypeTemplateVEIPPortConfigEntry 3 }
             
          onuTypeTemplateVEIPPortConfigRowStatus OBJECT-TYPE
              SYNTAX  RowStatus
              ACCESS  read-create
              STATUS  mandatory

              DESCRIPTION
                      ""
              ::= { onuTypeTemplateVEIPPortConfigEntry 4 }

-- ONU类型模版ONU IP Host配置 
 
       onuTypeTemplateIPHostParamConfigTable OBJECT-TYPE
                 SYNTAX  SEQUENCE OF OnuTypeTemplateIPHostParamConfigEntry
                 ACCESS  not-accessible
                 STATUS  mandatory
                 DESCRIPTION
                          "Onu type template IP Host config table."
                 ::= { nmsGponOnuTypeTemplateObj 6 }
 
             onuTypeTemplateIPHostParamConfigEntry OBJECT-TYPE
                 SYNTAX OnuTypeTemplateIPHostParamConfigEntry
                 ACCESS  not-accessible
                 STATUS  mandatory
                 DESCRIPTION
                          "Onu type template IP Host config table entry."
                 INDEX { onuTypeTemplateIPHostParamConfigTemplateIndex, onuTypeTemplateIPHostParamConfigPortIndex }
               ::= { onuTypeTemplateIPHostParamConfigTable 1 }   

             OnuTypeTemplateIPHostParamConfigEntry ::=
                 SEQUENCE {
                     onuTypeTemplateIPHostParamConfigTemplateIndex
                         INTEGER,       
                     onuTypeTemplateIPHostParamConfigPortIndex
                         INTEGER,
                     onuTypeTemplateIPHostParamConfigDHCP
                         INTEGER,
                     onuTypeTemplateIPHostParamConfigIPAddr
                         IpAddress,
                     onuTypeTemplateIPHostParamConfigNetmask   
                         IpAddress,
                     onuTypeTemplateIPHostParamConfigGateway 
                         IpAddress, 
                     onuTypeTemplateIPHostParamConfigPriDns 
                         IpAddress,
                     onuTypeTemplateIPHostParamConfigSecDns  
                         IpAddress,
                     onuTypeTemplateIPHostParamConfigRowStatus
                         RowStatus,
                     onuTypeTemplateIPHostParamConfigOption
                         INTEGER
            }
                 
                 
          onuTypeTemplateIPHostParamConfigTemplateIndex OBJECT-TYPE
              SYNTAX  INTEGER
              ACCESS  read-only
              STATUS  mandatory

              DESCRIPTION
                      ""
              ::= { onuTypeTemplateIPHostParamConfigEntry 1 }   
              
          onuTypeTemplateIPHostParamConfigPortIndex OBJECT-TYPE
              SYNTAX  INTEGER
              ACCESS  read-only
              STATUS  mandatory

              DESCRIPTION
                      ""
              ::= { onuTypeTemplateIPHostParamConfigEntry 2 }

           onuTypeTemplateIPHostParamConfigDHCP OBJECT-TYPE
              SYNTAX  INTEGER{
                        enable(1),
                        disable(2)
              }
              ACCESS  read-write
              STATUS  mandatory

              DESCRIPTION
                      "1-Enable,2-Disable."
              ::= { onuTypeTemplateIPHostParamConfigEntry 3 }
              
           onuTypeTemplateIPHostParamConfigIPAddr OBJECT-TYPE
              SYNTAX  IpAddress
              ACCESS  read-write
              STATUS  mandatory

              DESCRIPTION
                      "IP Address: A.A.A.A"
              ::= { onuTypeTemplateIPHostParamConfigEntry 4 }              
                           
           onuTypeTemplateIPHostParamConfigNetmask OBJECT-TYPE
              SYNTAX  IpAddress
              ACCESS  read-write
              STATUS  mandatory

              DESCRIPTION
                      "Netmask: A.A.A.A"
              ::= { onuTypeTemplateIPHostParamConfigEntry 5 } 
              
           onuTypeTemplateIPHostParamConfigGateway OBJECT-TYPE
              SYNTAX  IpAddress
              ACCESS  read-write
              STATUS  mandatory

              DESCRIPTION
                      "Gateway: A.A.A.A"
              ::= { onuTypeTemplateIPHostParamConfigEntry 6 }              
              
           onuTypeTemplateIPHostParamConfigPriDns OBJECT-TYPE
              SYNTAX  IpAddress
              ACCESS  read-write
              STATUS  mandatory

              DESCRIPTION
                      "Priority DNS: A.A.A.A"
              ::= { onuTypeTemplateIPHostParamConfigEntry 7 }
              
           onuTypeTemplateIPHostParamConfigSecDns OBJECT-TYPE
              SYNTAX  IpAddress
              ACCESS  read-write
              STATUS  mandatory

              DESCRIPTION
                      "Second DNS: A.A.A.A"
              ::= { onuTypeTemplateIPHostParamConfigEntry 8 }                            
              
           onuTypeTemplateIPHostParamConfigRowStatus OBJECT-TYPE
              SYNTAX  RowStatus
              ACCESS  read-create
              STATUS  mandatory

              DESCRIPTION
                      ""
              ::= { onuTypeTemplateIPHostParamConfigEntry 9 }

           onuTypeTemplateIPHostParamConfigOption OBJECT-TYPE
              SYNTAX  INTEGER
              ACCESS  read-write
              STATUS  mandatory

              DESCRIPTION
                      "IP-host IP options, config bit map:
                      0x01      Enable DHCP
                      0x02      Respond to pings
                      0x04      Respond to traceroute messages
                      0x08      Enable IP stack
                      0xFFFF    Not config IP options"
              ::= { onuTypeTemplateIPHostParamConfigEntry 10 }

-- ONU类型模版虚端口配置表

             onuTypeTemplateVirPortConfigTable OBJECT-TYPE
                 SYNTAX  SEQUENCE OF OnuTypeTemplateVirPortConfigEntry
                 ACCESS  not-accessible
                 STATUS  mandatory
                 DESCRIPTION
                          "Onu type template VIR port config table."
                 ::= { nmsGponOnuTypeTemplateObj 7 }

             onuTypeTemplateVirPortConfigEntry OBJECT-TYPE
                 SYNTAX OnuTypeTemplateVirPortConfigEntry
                 ACCESS  not-accessible
                 STATUS  mandatory
                 DESCRIPTION
                          "Onu type template VIR port config table entry."
                 INDEX { onuTypeTemplateVirPortConfigTemplateIndex, onuTypeTemplateVirPortConfigPortIndex }
             ::= { onuTypeTemplateVirPortConfigTable 1 }

             OnuTypeTemplateVirPortConfigEntry ::=
                 SEQUENCE {
                     onuTypeTemplateVirPortConfigTemplateIndex
                         INTEGER,
                     onuTypeTemplateVirPortConfigPortIndex
                         INTEGER,
                     onuTypeTemplateVirPortConfigTCONTID
                         INTEGER,
                     onuTypeTemplateVirPortConfigOltGEMPortID
                         INTEGER,
                     onuTypeTemplateVirPortConfigOltAllocID
                         INTEGER,
                     onuTypeTemplateVirPortConfigVirPortAdminState
                         INTEGER,
                     onuTypeTemplateVirPortConfigEncryptionMode
                         INTEGER,
                     onuTypeTemplateVirPortConfigDownstreamRateLimit
                         INTEGER,
                     onuTypeTemplateVirPortConfigOltVLANTranslationProfileID
                         INTEGER,
                     onuTypeTemplateVirPortConfigONUMacFilterProfileID
                         INTEGER,
                     onuTypeTemplateVirPortConfigONUMacFilterPreassignProfileID
                         INTEGER,
                     onuTypeTemplateVirPortConfigRowStatus
                         RowStatus,
                     onuTypeTemplateVirPortConfigDownstreamRateLimitPir
                         INTEGER
            }
                 
                 
          onuTypeTemplateVirPortConfigTemplateIndex OBJECT-TYPE
              SYNTAX  INTEGER
              ACCESS  read-only
              STATUS  mandatory

              DESCRIPTION
                      ""
              ::= { onuTypeTemplateVirPortConfigEntry 1 }

          onuTypeTemplateVirPortConfigPortIndex OBJECT-TYPE
              SYNTAX  INTEGER
              ACCESS  read-only
              STATUS  mandatory

              DESCRIPTION
                      ""
              ::= { onuTypeTemplateVirPortConfigEntry 2 }

          onuTypeTemplateVirPortConfigTCONTID OBJECT-TYPE
              SYNTAX  INTEGER
              ACCESS  read-write
              STATUS  mandatory

              DESCRIPTION
                      "Static T-CONT index from ONU’s perspective. Default value is 1. "
              ::= { onuTypeTemplateVirPortConfigEntry 3 }
          onuTypeTemplateVirPortConfigOltGEMPortID OBJECT-TYPE
              SYNTAX  INTEGER
              ACCESS  read-write
              STATUS  mandatory

              DESCRIPTION
                      "EM port no which is assigned dynamically by OLT. "
              ::= { onuTypeTemplateVirPortConfigEntry 4 }
          onuTypeTemplateVirPortConfigOltAllocID OBJECT-TYPE
              SYNTAX  INTEGER
              ACCESS  read-write
              STATUS  mandatory

              DESCRIPTION
                      "lloc-ID which is assigned dynamically by OLT, a dynamic Alloc-ID is one-to-one mapped 
                      to a static T-CONT index."
              ::= { onuTypeTemplateVirPortConfigEntry 5 }
          onuTypeTemplateVirPortConfigVirPortAdminState OBJECT-TYPE
              SYNTAX  INTEGER{
                               no-shutdown-unlocks(1),
                               shutdown-locks(2)
                             }

              ACCESS  read-write
              STATUS  mandatory

              DESCRIPTION
                      "This attribute locks and unlocks the functions performed by this managed entity. 1 No
                       shutdown/unlocks, 2 Shutdown/locks. "
              ::= { onuTypeTemplateVirPortConfigEntry 6 }
          onuTypeTemplateVirPortConfigEncryptionMode OBJECT-TYPE
              SYNTAX  INTEGER{
                               enable(1),
                               disable(2)
                             }

              ACCESS  read-write
              STATUS  mandatory

              DESCRIPTION
                      "The encryption mode for the GEM port. Possible values are: 1 (Enabled), 2 (Disabled). "
              ::= { onuTypeTemplateVirPortConfigEntry 7 }
          onuTypeTemplateVirPortConfigDownstreamRateLimit OBJECT-TYPE
              SYNTAX  INTEGER
              ACCESS  read-write
              STATUS  mandatory

              DESCRIPTION
                      "Config Virtual port downstream rate limit(unit:64kbps).
                      If onuTypeTemplateVirPortConfigDownstreamRateLimitPir equals 0, RFC2697(srTCM) policy is used. onuTypeTemplateVirPortConfigDownstreamRateLimit act as the CIR of RFC2697.
                      If onuTypeTemplateVirPortConfigDownstreamRateLimitPir is not 0, RFC2698(trTCM) policy is used. onuTypeTemplateVirPortConfigDownstreamRateLimitPir act as the PIR, and onuTypeTemplateVirPortConfigDownstreamRateLimit act as the CIR of RFC2698. onuTypeTemplateVirPortConfigDownstreamRateLimit should be less or equal than onuTypeTemplateVirPortConfigDownstreamRateLimitPir."
              ::= { onuTypeTemplateVirPortConfigEntry 8 }
          onuTypeTemplateVirPortConfigOltVLANTranslationProfileID OBJECT-TYPE
              SYNTAX  INTEGER(1..1024)
              ACCESS  read-write
              STATUS  mandatory

              DESCRIPTION
                      "It stores the profileIndex1 of the associated OLT VLAN translation profile. 1–1024."
              ::= { onuTypeTemplateVirPortConfigEntry 9 }
          onuTypeTemplateVirPortConfigONUMacFilterProfileID OBJECT-TYPE
              SYNTAX  INTEGER
              ACCESS  read-write
              STATUS  mandatory

              DESCRIPTION
                      ""
              ::= { onuTypeTemplateVirPortConfigEntry 10 }
          onuTypeTemplateVirPortConfigONUMacFilterPreassignProfileID OBJECT-TYPE
              SYNTAX  INTEGER
              ACCESS  read-write
              STATUS  mandatory

              DESCRIPTION
                      ""
              ::= { onuTypeTemplateVirPortConfigEntry 11 }
          onuTypeTemplateVirPortConfigRowStatus OBJECT-TYPE
              SYNTAX  RowStatus
              ACCESS  read-create
              STATUS  mandatory

              DESCRIPTION
                      ""
              ::= { onuTypeTemplateVirPortConfigEntry 12 }
          onuTypeTemplateVirPortConfigDownstreamRateLimitPir OBJECT-TYPE
              SYNTAX  INTEGER
              ACCESS  read-write
              STATUS  mandatory

              DESCRIPTION
                      "Config Virtual port downstream rate limit pir(unit:64kbps). 
                      If onuTypeTemplateVirPortConfigDownstreamRateLimitPir equals 0, RFC2697(srTCM) policy is used. onuTypeTemplateVirPortConfigDownstreamRateLimit act as the CIR of RFC2697.
                      If onuTypeTemplateVirPortConfigDownstreamRateLimitPir is not 0, RFC2698(trTCM) policy is used. onuTypeTemplateVirPortConfigDownstreamRateLimitPir act as the PIR, and onuTypeTemplateVirPortConfigDownstreamRateLimit act as the CIR of RFC2698. onuTypeTemplateVirPortConfigDownstreamRateLimit should be less or equal than onuTypeTemplateVirPortConfigDownstreamRateLimitPir."
              ::= { onuTypeTemplateVirPortConfigEntry 13 }

--ONU类型模版虚端口VLAN翻译表

             onuTypeTemplateVirPortDot1qTranslatTable OBJECT-TYPE
                 SYNTAX  SEQUENCE OF OnuTypeTemplateVirPortDot1qTranslatEntry
                 ACCESS  not-accessible
                 STATUS  mandatory
                 DESCRIPTION
                          "Config table for onu type template VLAN translation based on onu VIR port."
                 ::= { nmsGponOnuTypeTemplateObj 8 }

             onuTypeTemplateVirPortDot1qTranslatEntry OBJECT-TYPE
                 SYNTAX OnuTypeTemplateVirPortDot1qTranslatEntry
                 ACCESS  not-accessible
                 STATUS  mandatory
                 DESCRIPTION
                          "Config entry for onu type template VLAN translation based on onu VIR port."
                 INDEX { onuTypeTemplateVirPortDot1qTranslatTemplateIndex, onuTypeTemplateVirPortDot1qTranslatVirPortIndex, onuTypeTemplateVirPortDot1qTranslatEntryIndex }
             ::= { onuTypeTemplateVirPortDot1qTranslatTable 1 }

             OnuTypeTemplateVirPortDot1qTranslatEntry ::=
                 SEQUENCE {
                     onuTypeTemplateVirPortDot1qTranslatTemplateIndex
                         INTEGER,
                     onuTypeTemplateVirPortDot1qTranslatVirPortIndex
                         INTEGER,
                     onuTypeTemplateVirPortDot1qTranslatEntryIndex
                         INTEGER,
                     onuTypeTemplateVirPortDot1qTranslatMode
                         INTEGER,
                     onuTypeTemplateVirPortDot1qTranslatNto1
                         INTEGER,
                     onuTypeTemplateVirPortDot1qTranslatSorVlanStart
                         INTEGER,
                     onuTypeTemplateVirPortDot1qTranslatSorVlanEnd
                         INTEGER,
                     onuTypeTemplateVirPortDot1qTranslatSorVlanMap
                         OCTET STRING,
                     onuTypeTemplateVirPortDot1qTranslatDstVlan
                         INTEGER,
                     onuTypeTemplateVirPortDot1qTranslatMixVlan
                         INTEGER,
                     onuTypeTemplateVirPortDot1qTranslatPriority
                         INTEGER,
                     onuTypeTemplateVirPortDot1qTranslatRowStatus
                         RowStatus
            }
                 
                 
          onuTypeTemplateVirPortDot1qTranslatTemplateIndex OBJECT-TYPE
              SYNTAX  INTEGER
              ACCESS  read-only
              STATUS  mandatory

              DESCRIPTION
                      "ONU diID"
              ::= { onuTypeTemplateVirPortDot1qTranslatEntry 1 }

          onuTypeTemplateVirPortDot1qTranslatVirPortIndex OBJECT-TYPE
              SYNTAX  INTEGER
              ACCESS  read-only
              STATUS  mandatory

              DESCRIPTION
                      "ONU virtual port ID"
              ::= { onuTypeTemplateVirPortDot1qTranslatEntry 2 }

          onuTypeTemplateVirPortDot1qTranslatEntryIndex OBJECT-TYPE
              SYNTAX  INTEGER
              ACCESS  read-only
              STATUS  mandatory

              DESCRIPTION
                      "ONU virtual VLAN translation config entry index"
              ::= { onuTypeTemplateVirPortDot1qTranslatEntry 3 }

          onuTypeTemplateVirPortDot1qTranslatMode OBJECT-TYPE
              SYNTAX  INTEGER{
                               flat(1),
                               qinq(2),
                               mix(3),
                               range-flat(4),
                               range-qinq(5)
                             }
              ACCESS  read-write
              STATUS  mandatory

              DESCRIPTION
                      "Vlan translation mode:
                            1--flat;
                            2--QinQ;
                            3--mix;
                            4--range flat;
                            5--range QinQ."
              ::= { onuTypeTemplateVirPortDot1qTranslatEntry 4 }

          onuTypeTemplateVirPortDot1qTranslatNto1 OBJECT-TYPE
              SYNTAX  INTEGER{
                                oto1(1),
                                nto1(2)
                             }
              ACCESS  read-write
              STATUS  mandatory

              DESCRIPTION
                      "1--1to1; 2--nto1."
              ::= { onuTypeTemplateVirPortDot1qTranslatEntry 5 }

          onuTypeTemplateVirPortDot1qTranslatSorVlanStart OBJECT-TYPE
              SYNTAX  INTEGER
              ACCESS  read-write
              STATUS  mandatory

              DESCRIPTION
                      "Start VLAN ID(1-4094)."
              ::= { onuTypeTemplateVirPortDot1qTranslatEntry 6 }

          onuTypeTemplateVirPortDot1qTranslatSorVlanEnd OBJECT-TYPE
              SYNTAX  INTEGER
              ACCESS  read-write
              STATUS  mandatory

              DESCRIPTION
                      "End VLAN ID(1-4094)."
              ::= { onuTypeTemplateVirPortDot1qTranslatEntry 7 }

          onuTypeTemplateVirPortDot1qTranslatSorVlanMap OBJECT-TYPE
              SYNTAX  OCTET STRING
              ACCESS  read-write
              STATUS  mandatory

              DESCRIPTION
                      "Source VLAN IDs such as (1,3,5,7) Or (1,3-5,7) Or (1-7)."
              ::= { onuTypeTemplateVirPortDot1qTranslatEntry 8 } 
 
          onuTypeTemplateVirPortDot1qTranslatDstVlan OBJECT-TYPE
              SYNTAX  INTEGER
              ACCESS  read-write
              STATUS  mandatory

              DESCRIPTION
                      "Destination VLAN ID(1-4094)."
              ::= { onuTypeTemplateVirPortDot1qTranslatEntry 9 }
              
          onuTypeTemplateVirPortDot1qTranslatMixVlan OBJECT-TYPE
              SYNTAX  INTEGER
              ACCESS  read-write
              STATUS  mandatory

              DESCRIPTION
                      "Mix out VLAN ID(1-4094)."
              ::= { onuTypeTemplateVirPortDot1qTranslatEntry 10 } 

          onuTypeTemplateVirPortDot1qTranslatPriority OBJECT-TYPE
              SYNTAX  INTEGER
              ACCESS  read-write
              STATUS  mandatory

              DESCRIPTION
                      "New 802.1Q priority value(0-7)."
              ::= { onuTypeTemplateVirPortDot1qTranslatEntry 11 } 

          onuTypeTemplateVirPortDot1qTranslatRowStatus OBJECT-TYPE
              SYNTAX  RowStatus
              ACCESS  read-write
              STATUS  mandatory

              DESCRIPTION
                      ""
              ::= { onuTypeTemplateVirPortDot1qTranslatEntry 12 }  

--ONU类型模版Video端口配置 
             onuTypeTemplateVideoPortConfigTable OBJECT-TYPE
                 SYNTAX  SEQUENCE OF OnuTypeTemplateVideoPortConfigEntry
                 ACCESS  not-accessible
                 STATUS  mandatory
                 DESCRIPTION
                          "ONU type template Video port config table."
                 ::= { nmsGponOnuTypeTemplateObj 9 }

             onuTypeTemplateVideoPortConfigEntry OBJECT-TYPE
                 SYNTAX OnuTypeTemplateVideoPortConfigEntry
                 ACCESS  not-accessible
                 STATUS  mandatory
                 DESCRIPTION
                          "ONU type template Video port config table entry."
                 INDEX { onuTypeTemplateVideoPortConfigTemplateIndex,  onuTypeTemplateVideoPortConfigPortIndex}
             ::= { onuTypeTemplateVideoPortConfigTable 1 }

             OnuTypeTemplateVideoPortConfigEntry ::=
                 SEQUENCE {
                     onuTypeTemplateVideoPortConfigTemplateIndex
                         INTEGER,
                     onuTypeTemplateVideoPortConfigPortIndex 
                         INTEGER,
                     onuTypeTemplateVideoPortConfigAdminState
                         INTEGER,
                     onuTypeTemplateVideoPortConfigCatvProfileID
                         INTEGER,
                     onuTypeTemplateVideoPortConfigRowStatus
                         RowStatus               
                 }

          onuTypeTemplateVideoPortConfigTemplateIndex OBJECT-TYPE
              SYNTAX  INTEGER
              ACCESS  read-only
              STATUS  mandatory
              DESCRIPTION
                      "Index of the table, ONU port index."
              ::= { onuTypeTemplateVideoPortConfigEntry 1 }
                 
          onuTypeTemplateVideoPortConfigPortIndex OBJECT-TYPE
              SYNTAX  INTEGER
              ACCESS  read-only
              STATUS  mandatory
              DESCRIPTION
                      "Index of the table, video port index "
              ::= { onuTypeTemplateVideoPortConfigEntry 2 }
              
          onuTypeTemplateVideoPortConfigAdminState OBJECT-TYPE
              SYNTAX  INTEGER{
                        no-shutdown(1),
                        shutdown(2)
                        }              
              ACCESS  read-write
              STATUS  mandatory
              DESCRIPTION
                      "1-No shutdown  2-Shutdown "
              ::= { onuTypeTemplateVideoPortConfigEntry 3 }
                 
          onuTypeTemplateVideoPortConfigCatvProfileID OBJECT-TYPE
              SYNTAX  INTEGER
              ACCESS  read-write
              STATUS  mandatory
              DESCRIPTION
                      "It points to the associated Catv profile. 0 means cancel profile config."
              ::= { onuTypeTemplateVideoPortConfigEntry 4 }
              
          onuTypeTemplateVideoPortConfigRowStatus OBJECT-TYPE
              SYNTAX  RowStatus
              ACCESS  read-create
              STATUS  mandatory

              DESCRIPTION
                      ""
              ::= { onuTypeTemplateVideoPortConfigEntry 5 } 

--ONU类型模版Wan端口基本配置

             onuTypeTemplateWanPortConfigTable OBJECT-TYPE
                 SYNTAX  SEQUENCE OF OnuTypeTemplateWanPortConfigEntry
                 ACCESS  not-accessible
                 STATUS  mandatory
                 DESCRIPTION
                          "ONU type template Wan port config table."
                 ::= { nmsGponOnuTypeTemplateObj 10 }

             onuTypeTemplateWanPortConfigEntry OBJECT-TYPE
                 SYNTAX OnuTypeTemplateWanPortConfigEntry
                 ACCESS  not-accessible
                 STATUS  mandatory
                 DESCRIPTION
                          "ONU type template Wan port config table entry."
                 INDEX { onuTypeTemplateWanPortConfigTemplateIndex,  onuTypeTemplateWanPortConfigPortIndex}
             ::= { onuTypeTemplateWanPortConfigTable 1 }

             OnuTypeTemplateWanPortConfigEntry ::=
                 SEQUENCE {
                     onuTypeTemplateWanPortConfigTemplateIndex
                         INTEGER,
                     onuTypeTemplateWanPortConfigPortIndex 
                         INTEGER,
                     onuTypeTemplateWanPortConfigAdminState
                         INTEGER,
                     onuTypeTemplateWanPortConfigNat 
                         INTEGER,
                     onuTypeTemplateWanPortConfigMtu
                         INTEGER,
                     onuTypeTemplateWanPortConfigDialOnDemandTimeout
                         INTEGER,
                     onuTypeTemplateWanPortConfigAutoGetAddress
                         INTEGER, 
                     onuTypeTemplateWanPortConfigConnectionType
                         INTEGER,
                    onuTypeTemplateWanPortConfigipVersion 
                         INTEGER,
                     onuTypeTemplateWanPortConfigautoGetIpv6Address
                         INTEGER,
                     onuTypeTemplateWanPortConfigdhcpv6PrefixDelegation
                         INTEGER,
                     onuTypeTemplateWanPortConfigautoGetDnsAddress
                         INTEGER, 
                     onuTypeTemplateWanPortConfiglanDhcp
                         INTEGER,
                     onuTypeTemplateWanPortConfigClear
                         BITS,
                     onuTypeTemplateWanPortConfigRowStatus
                         RowStatus               
                 }

          onuTypeTemplateWanPortConfigTemplateIndex OBJECT-TYPE
              SYNTAX  INTEGER
              ACCESS  read-only
              STATUS  mandatory
              DESCRIPTION
                      "Index of the table, ONU port index."
              ::= { onuTypeTemplateWanPortConfigEntry 1 }
                 
          onuTypeTemplateWanPortConfigPortIndex OBJECT-TYPE
              SYNTAX  INTEGER
              ACCESS  read-only
              STATUS  mandatory
              DESCRIPTION
                      "Index of the table, wan port index "
              ::= { onuTypeTemplateWanPortConfigEntry 2 }
              
          onuTypeTemplateWanPortConfigAdminState OBJECT-TYPE
              SYNTAX  INTEGER{
                        enable(1),
                        disable(2)
                        }
              ACCESS  read-write
              STATUS  mandatory
              DESCRIPTION
                      "1-Enable；2-Disable "
              ::= { onuTypeTemplateWanPortConfigEntry 3 }
              
          onuTypeTemplateWanPortConfigNat OBJECT-TYPE
              SYNTAX  INTEGER{
                        enable(1),
                        disable(2)
                        }
              ACCESS  read-write
              STATUS  mandatory
              DESCRIPTION
                      "1-Enable；2-Disable"
              ::= { onuTypeTemplateWanPortConfigEntry 4 }
                 
          onuTypeTemplateWanPortConfigMtu OBJECT-TYPE
              SYNTAX  INTEGER
              ACCESS  read-write
              STATUS  mandatory
              DESCRIPTION
                      "MTU（1-65535） "
              ::= { onuTypeTemplateWanPortConfigEntry 5 }
              
          onuTypeTemplateWanPortConfigDialOnDemandTimeout OBJECT-TYPE
              SYNTAX  INTEGER           
              ACCESS  read-write
              STATUS  mandatory
              DESCRIPTION
                      "On demand timeou（0-65535）:
                        0--dial always
                        1-65535--dial on demand"
              ::= { onuTypeTemplateWanPortConfigEntry 6 }
                 
          onuTypeTemplateWanPortConfigAutoGetAddress OBJECT-TYPE
              SYNTAX  INTEGER{
                        enable(1),
                        disable(2)
                        }
              ACCESS  read-write
              STATUS  mandatory
              DESCRIPTION
                      "1-Enable；2-Disable"
              ::= { onuTypeTemplateWanPortConfigEntry 7 }
              
          onuTypeTemplateWanPortConfigConnectionType OBJECT-TYPE
              SYNTAX  INTEGER{
                    bridge(1),
                    dhcp(2),
                    static(3),
                    pppoe(4),
                    pppoe_bridge(5),
                    pppoe_mix(6)
                    }           
              ACCESS  read-write
              STATUS  mandatory
              DESCRIPTION
                      "Connection Type:
                        1--bridge
                        2--DHCP
                        3--static
                        4--PPPOE
                        5--PPPOE_bridge
                        6--PPPOE_mix "
              ::= { onuTypeTemplateWanPortConfigEntry 8 }

          onuTypeTemplateWanPortConfigipVersion OBJECT-TYPE
              SYNTAX  INTEGER{
                        ipv4(1),
                        ipv6(2),
                        ipv4-ipv6(3)
                        }
              ACCESS  read-write
              STATUS  mandatory
              DESCRIPTION
                      "1-ipv4；2-ipv6；3-ipv4/ipv6 "
              ::= { onuTypeTemplateWanPortConfigEntry 9 }

          onuTypeTemplateWanPortConfigautoGetIpv6Address OBJECT-TYPE
              SYNTAX  INTEGER{
                        enable(1),
                        disable(2)
                        }
              ACCESS  read-write
              STATUS  mandatory
              DESCRIPTION
                      "1-Enable；2-Disable "
              ::= { onuTypeTemplateWanPortConfigEntry 10 }
              
          onuTypeTemplateWanPortConfigdhcpv6PrefixDelegation OBJECT-TYPE
              SYNTAX  INTEGER{
                        enable(1),
                        disable(2)
                        }
              ACCESS  read-write
              STATUS  mandatory
              DESCRIPTION
                      "1-Enable；2-Disable "
              ::= { onuTypeTemplateWanPortConfigEntry 11 }
              
          onuTypeTemplateWanPortConfigautoGetDnsAddress OBJECT-TYPE
              SYNTAX  INTEGER{
                        enable(1),
                        disable(2)
                        }
              ACCESS  read-write
              STATUS  mandatory
              DESCRIPTION
                      "1-Enable；2-Disable "
              ::= { onuTypeTemplateWanPortConfigEntry 12 }
              
          onuTypeTemplateWanPortConfiglanDhcp OBJECT-TYPE
              SYNTAX  INTEGER{
                        enable(1),
                        disable(2)
                        }
              ACCESS  read-write
              STATUS  mandatory
              DESCRIPTION
                      "1-Enable；2-Disable "
              ::= { onuTypeTemplateWanPortConfigEntry 13 } 
              
          onuTypeTemplateWanPortConfigClear OBJECT-TYPE
              SYNTAX  BITS{    
                        adminState(0),
                        connectionType(1),
                        serviceType(2),
                        nat(3),
                        mtu(4),
                        dialMode(5),
                        autoGetIpv4Address(6),
                        ipv4(7),
                        tci(8),
                        portBind(9),
                        pppoeNamePwd(10),
                        connectionName(11),
                        ipVersion(12),
                        ipv6(13),
                        autoGetIpv6Address(14),
                        dhcpv6PrefixDelegation(15),
                        autoGetDnsAddress(16),
                        pppoeServiceName(17),
                        lanDhcp(18)
                        }
              ACCESS  read-write
              STATUS  mandatory
              DESCRIPTION
                      "Clear the WAN port config, every bit mean one config, 32 bits."
              ::= { onuTypeTemplateWanPortConfigEntry 14 }
              
              
          onuTypeTemplateWanPortConfigRowStatus OBJECT-TYPE
              SYNTAX  RowStatus
              ACCESS  read-create
              STATUS  mandatory
              DESCRIPTION
                      ""
              ::= { onuTypeTemplateWanPortConfigEntry 15 } 
              
--ONU类型模版Wan端口连接配置

             onuTypeTemplateWanPortConfigLinkTable OBJECT-TYPE
                 SYNTAX  SEQUENCE OF OnuTypeTemplateWanPortConfigLinkEntry
                 ACCESS  not-accessible
                 STATUS  mandatory
                 DESCRIPTION
                          "ONU type template Wan port config link table."
                 ::= { nmsGponOnuTypeTemplateObj 11 }

             onuTypeTemplateWanPortConfigLinkEntry OBJECT-TYPE
                 SYNTAX OnuTypeTemplateWanPortConfigLinkEntry
                 ACCESS  not-accessible
                 STATUS  mandatory
                 DESCRIPTION
                          "ONU type template Wan port config link table entry."
                 INDEX { onuTypeTemplateWanPortConfigLinkTemplateIndex,  onuTypeTemplateWanPortConfigLinkPortIndex}
             ::= { onuTypeTemplateWanPortConfigLinkTable 1 }

             OnuTypeTemplateWanPortConfigLinkEntry ::=
                 SEQUENCE {
                     onuTypeTemplateWanPortConfigLinkTemplateIndex
                         INTEGER,
                     onuTypeTemplateWanPortConfigLinkPortIndex 
                         INTEGER,
                     onuTypeTemplateWanPortConfigLinkServiceTypeInternet
                         INTEGER,
                     onuTypeTemplateWanPortConfigLinkServiceTypeVoip
                         INTEGER,
                     onuTypeTemplateWanPortConfigLinkServiceTypeTr069
                         INTEGER,
                     onuTypeTemplateWanPortConfigLinkServiceTypeOther
                         INTEGER,
                     onuTypeTemplateWanPortConfigLinkRowStatus
                         RowStatus               
                 }

          onuTypeTemplateWanPortConfigLinkTemplateIndex OBJECT-TYPE
              SYNTAX  INTEGER
              ACCESS  read-only
              STATUS  mandatory
              DESCRIPTION
                      "Index of the table, ONU port index."
              ::= { onuTypeTemplateWanPortConfigLinkEntry 1 }
                 
          onuTypeTemplateWanPortConfigLinkPortIndex OBJECT-TYPE
              SYNTAX  INTEGER
              ACCESS  read-only
              STATUS  mandatory
              DESCRIPTION
                      "Index of the table, wan port index "
              ::= { onuTypeTemplateWanPortConfigLinkEntry 2 }
                 
          onuTypeTemplateWanPortConfigLinkServiceTypeInternet OBJECT-TYPE
              SYNTAX  INTEGER{
                    enable(1),
                    disable(2)
                    }
              ACCESS  read-write
              STATUS  mandatory
              DESCRIPTION
                      "Internet Service Type:
                        1--Enable
                        2--Disable"
              ::= { onuTypeTemplateWanPortConfigLinkEntry 3 } 
              
          onuTypeTemplateWanPortConfigLinkServiceTypeVoip OBJECT-TYPE
              SYNTAX  INTEGER{
                    enable(1),
                    disable(2)
                    }
              ACCESS  read-write
              STATUS  mandatory
              DESCRIPTION
                      "Voip Service Type:
                        1--Enable
                        2--Disable"
              ::= { onuTypeTemplateWanPortConfigLinkEntry 4 }
              
          onuTypeTemplateWanPortConfigLinkServiceTypeTr069 OBJECT-TYPE
              SYNTAX  INTEGER{
                    enable(1),
                    disable(2)
                    }
              ACCESS  read-write
              STATUS  mandatory
              DESCRIPTION
                      "Tr069 Service Type:
                        1--Enable
                        2--Disable"
              ::= { onuTypeTemplateWanPortConfigLinkEntry 5 }
              
           onuTypeTemplateWanPortConfigLinkServiceTypeOther OBJECT-TYPE
              SYNTAX  INTEGER{
                    enable(1),
                    disable(2)
                    }
              ACCESS  read-write
              STATUS  mandatory
              DESCRIPTION
                      "Other Service Type:
                        1--Enable
                        2--Disable"
              ::= { onuTypeTemplateWanPortConfigLinkEntry 6 }
              
           onuTypeTemplateWanPortConfigLinkRowStatus OBJECT-TYPE
              SYNTAX  RowStatus
              ACCESS  read-create
              STATUS  mandatory
              DESCRIPTION
                      ""
              ::= { onuTypeTemplateWanPortConfigLinkEntry 7 } 

--ONU类型模版Wan端口Ip配置

             onuTypeTemplateWanPortConfigIpTable OBJECT-TYPE
                 SYNTAX  SEQUENCE OF OnuTypeTemplateWanPortConfigIpEntry
                 ACCESS  not-accessible
                 STATUS  mandatory
                 DESCRIPTION
                          "ONU type template Wan port config ip table."
                 ::= { nmsGponOnuTypeTemplateObj 12 }

             onuTypeTemplateWanPortConfigIpEntry OBJECT-TYPE
                 SYNTAX OnuTypeTemplateWanPortConfigIpEntry
                 ACCESS  not-accessible
                 STATUS  mandatory
                 DESCRIPTION
                          "ONU type template Wan port config ip table entry."
                 INDEX { onuTypeTemplateWanPortConfigIpTemplateIndex,  onuTypeTemplateWanPortConfigIpPortIndex}
             ::= { onuTypeTemplateWanPortConfigIpTable 1 }

             OnuTypeTemplateWanPortConfigIpEntry ::=
                 SEQUENCE {
                     onuTypeTemplateWanPortConfigIpTemplateIndex
                         INTEGER,
                     onuTypeTemplateWanPortConfigIpPortIndex 
                         INTEGER,
                     onuTypeTemplateWanPortConfigIpAddress
                         IpAddress,
                     onuTypeTemplateWanPortConfigIpMask
                         IpAddress,
                     onuTypeTemplateWanPortConfigIpGateway 
                         IpAddress,
                     onuTypeTemplateWanPortConfigIpPriDns
                         IpAddress,
                     onuTypeTemplateWanPortConfigIpSecDns
                         IpAddress,
                     onuTypeTemplateWanPortConfigIpRowStatus
                         RowStatus               
                 }

          onuTypeTemplateWanPortConfigIpTemplateIndex OBJECT-TYPE
              SYNTAX  INTEGER
              ACCESS  read-only
              STATUS  mandatory
              DESCRIPTION
                      "Index of the table, ONU port index."
              ::= { onuTypeTemplateWanPortConfigIpEntry 1 }
                 
          onuTypeTemplateWanPortConfigIpPortIndex OBJECT-TYPE
              SYNTAX  INTEGER
              ACCESS  read-only
              STATUS  mandatory
              DESCRIPTION
                      "Index of the table, wan port index "
              ::= { onuTypeTemplateWanPortConfigIpEntry 2 }
              
          onuTypeTemplateWanPortConfigIpAddress OBJECT-TYPE
              SYNTAX  IpAddress              
              ACCESS  read-write
              STATUS  mandatory
              DESCRIPTION
                      "IP Address: A.A.A.A "
              ::= { onuTypeTemplateWanPortConfigIpEntry 3 }
                 
          onuTypeTemplateWanPortConfigIpMask OBJECT-TYPE
              SYNTAX  IpAddress
              ACCESS  read-write
              STATUS  mandatory
              DESCRIPTION
                      "Netmask: A.A.A.A"
              ::= { onuTypeTemplateWanPortConfigIpEntry 4 } 
              
          onuTypeTemplateWanPortConfigIpGateway OBJECT-TYPE
              SYNTAX  IpAddress
              ACCESS  read-write
              STATUS  mandatory
              DESCRIPTION
                      "Gateway: A.A.A.A"
              ::= { onuTypeTemplateWanPortConfigIpEntry 5 }
                 
          onuTypeTemplateWanPortConfigIpPriDns OBJECT-TYPE
              SYNTAX  IpAddress
              ACCESS  read-write
              STATUS  mandatory
              DESCRIPTION
                      "Primary DNS: A.A.A.A"
              ::= { onuTypeTemplateWanPortConfigIpEntry 6 }
              
          onuTypeTemplateWanPortConfigIpSecDns OBJECT-TYPE
              SYNTAX  IpAddress           
              ACCESS  read-write
              STATUS  mandatory
              DESCRIPTION
                      "Secondary DNS: A.A.A.A"
              ::= { onuTypeTemplateWanPortConfigIpEntry 7 }
              
          onuTypeTemplateWanPortConfigIpRowStatus OBJECT-TYPE
              SYNTAX  RowStatus
              ACCESS  read-create
              STATUS  mandatory
              DESCRIPTION
                      ""
              ::= { onuTypeTemplateWanPortConfigIpEntry 8 } 


--ONU类型模版Wan端口Tci配置

             onuTypeTemplateWanPortConfigTciTable OBJECT-TYPE
                 SYNTAX  SEQUENCE OF OnuTypeTemplateWanPortConfigTciEntry
                 ACCESS  not-accessible
                 STATUS  mandatory
                 DESCRIPTION
                          "ONU type template Wan port config tci table."
                 ::= { nmsGponOnuTypeTemplateObj 13 }

             onuTypeTemplateWanPortConfigTciEntry OBJECT-TYPE
                 SYNTAX OnuTypeTemplateWanPortConfigTciEntry
                 ACCESS  not-accessible
                 STATUS  mandatory
                 DESCRIPTION
                          "ONU type template Wan port config tci table entry."
                 INDEX { onuTypeTemplateWanPortConfigTciTemplateIndex,  onuTypeTemplateWanPortConfigTciPortIndex}
             ::= { onuTypeTemplateWanPortConfigTciTable 1 }

             OnuTypeTemplateWanPortConfigTciEntry ::=
                 SEQUENCE {
                     onuTypeTemplateWanPortConfigTciTemplateIndex
                         INTEGER,
                     onuTypeTemplateWanPortConfigTciPortIndex 
                         INTEGER,
                     onuTypeTemplateWanPortConfigTciVlanId
                         INTEGER,
                     onuTypeTemplateWanPortConfigTciPri
                         INTEGER,
                     onuTypeTemplateWanPortConfigTciDei 
                         INTEGER,
                     onuTypeTemplateWanPortConfigTciRowStatus
                         RowStatus               
                 }       

          onuTypeTemplateWanPortConfigTciTemplateIndex OBJECT-TYPE
              SYNTAX  INTEGER
              ACCESS  read-only
              STATUS  mandatory
              DESCRIPTION
                      "Index of the table, ONU port index."
              ::= { onuTypeTemplateWanPortConfigTciEntry 1 }
                 
          onuTypeTemplateWanPortConfigTciPortIndex OBJECT-TYPE
              SYNTAX  INTEGER
              ACCESS  read-only
              STATUS  mandatory
              DESCRIPTION
                      "Index of the table, wan port index "
              ::= { onuTypeTemplateWanPortConfigTciEntry 2 }
              
          onuTypeTemplateWanPortConfigTciVlanId OBJECT-TYPE
              SYNTAX  INTEGER(0..4094)              
              ACCESS  read-write
              STATUS  mandatory
              DESCRIPTION
                      "Vlan ID(0-4094) 0 for vlan disable "
              ::= { onuTypeTemplateWanPortConfigTciEntry 3 }
                 
          onuTypeTemplateWanPortConfigTciPri OBJECT-TYPE
              SYNTAX  INTEGER(0..7)
              ACCESS  read-write
              STATUS  mandatory
              DESCRIPTION
                      "Priority(0-7)"
              ::= { onuTypeTemplateWanPortConfigTciEntry 4 } 
              
          onuTypeTemplateWanPortConfigTciDei OBJECT-TYPE
              SYNTAX  INTEGER(0..1)
              ACCESS  read-write
              STATUS  mandatory
              DESCRIPTION
                      "DEI(0,1)"
              ::= { onuTypeTemplateWanPortConfigTciEntry 5 }
                     
          onuTypeTemplateWanPortConfigTciRowStatus OBJECT-TYPE
              SYNTAX  RowStatus
              ACCESS  read-create
              STATUS  mandatory
              DESCRIPTION
                      ""
              ::= { onuTypeTemplateWanPortConfigTciEntry 6 } 


--ONU类型模版Wan端口绑定配置

             onuTypeTemplateWanPortConfigBindTable OBJECT-TYPE
                 SYNTAX  SEQUENCE OF OnuTypeTemplateWanPortConfigBindEntry
                 ACCESS  not-accessible
                 STATUS  mandatory
                 DESCRIPTION
                          "ONU type template Wan port config bind port table."
                 ::= { nmsGponOnuTypeTemplateObj 14 }

             onuTypeTemplateWanPortConfigBindEntry OBJECT-TYPE
                 SYNTAX OnuTypeTemplateWanPortConfigBindEntry
                 ACCESS  not-accessible
                 STATUS  mandatory
                 DESCRIPTION
                          "ONU type template Wan port config bind port table entry."
                 INDEX { onuTypeTemplateWanPortConfigBindTemplateIndex,  onuTypeTemplateWanPortConfigBindPortIndex}
             ::= { onuTypeTemplateWanPortConfigBindTable 1 }

             OnuTypeTemplateWanPortConfigBindEntry ::=
                 SEQUENCE {
                     onuTypeTemplateWanPortConfigBindTemplateIndex
                         INTEGER,
                     onuTypeTemplateWanPortConfigBindPortIndex 
                         INTEGER,
                     onuTypeTemplateWanPortConfigBindLan1
                         INTEGER,
                     onuTypeTemplateWanPortConfigBindLan2
                         INTEGER,
                     onuTypeTemplateWanPortConfigBindLan3 
                         INTEGER,
                     onuTypeTemplateWanPortConfigBindLan4
                         INTEGER,
                     onuTypeTemplateWanPortConfigBindSsid
                         BITS,
                     onuTypeTemplateWanPortConfigBindRowStatus
                         RowStatus               
                 }

          onuTypeTemplateWanPortConfigBindTemplateIndex OBJECT-TYPE
              SYNTAX  INTEGER
              ACCESS  read-only
              STATUS  mandatory
              DESCRIPTION
                      "Index of the table, ONU port index."
              ::= { onuTypeTemplateWanPortConfigBindEntry 1 }
                 
          onuTypeTemplateWanPortConfigBindPortIndex OBJECT-TYPE
              SYNTAX  INTEGER
              ACCESS  read-only
              STATUS  mandatory
              DESCRIPTION
                      "Index of the table, wan port index "
              ::= { onuTypeTemplateWanPortConfigBindEntry 2 }
              
          onuTypeTemplateWanPortConfigBindLan1 OBJECT-TYPE
              SYNTAX  INTEGER{
                        enable(1),
                        disable(2)
                        }
              ACCESS  read-write
              STATUS  mandatory
              DESCRIPTION
                      "1-Enable；2-Disable "
              ::= { onuTypeTemplateWanPortConfigBindEntry 3 }
                 
          onuTypeTemplateWanPortConfigBindLan2 OBJECT-TYPE
              SYNTAX  INTEGER{
                        enable(1),
                        disable(2)
                        }
              ACCESS  read-write
              STATUS  mandatory
              DESCRIPTION
                      "1-Enable；2-Disable"
              ::= { onuTypeTemplateWanPortConfigBindEntry 4 } 
              
          onuTypeTemplateWanPortConfigBindLan3 OBJECT-TYPE
              SYNTAX  INTEGER{
                        enable(1),
                        disable(2)
                        }
              ACCESS  read-write
              STATUS  mandatory
              DESCRIPTION
                      "1-Enable；2-Disable"
              ::= { onuTypeTemplateWanPortConfigBindEntry 5 }
                 
          onuTypeTemplateWanPortConfigBindLan4 OBJECT-TYPE
              SYNTAX  INTEGER{
                        enable(1),
                        disable(2)
                        }
              ACCESS  read-write
              STATUS  mandatory
              DESCRIPTION
                      "1-Enable；2-Disable "
              ::= { onuTypeTemplateWanPortConfigBindEntry 6 }
              
          onuTypeTemplateWanPortConfigBindSsid OBJECT-TYPE
              SYNTAX  BITS{
                        ssid1(0),
                        ssid2(1),
                        ssid3(2),
                        ssid4(3),
                        ssid5(4),
                        ssid6(5),
                        ssid7(6),
                        ssid8(7)
                        }
              ACCESS  read-write
              STATUS  mandatory
              DESCRIPTION
                      "Bridge bind ssid port, 8 bits represent 8 ssid, 0 is not bind, 1 is bind "
              ::= { onuTypeTemplateWanPortConfigBindEntry 7 }  
              
          onuTypeTemplateWanPortConfigBindRowStatus OBJECT-TYPE
              SYNTAX  RowStatus
              ACCESS  read-create
              STATUS  mandatory
              DESCRIPTION
                      ""
              ::= { onuTypeTemplateWanPortConfigBindEntry 8 } 


--ONU类型模版Wan端口Pppoe配置

             onuTypeTemplateWanPortConfigPppoeTable OBJECT-TYPE
                 SYNTAX  SEQUENCE OF OnuTypeTemplateWanPortConfigPppoeEntry
                 ACCESS  not-accessible
                 STATUS  mandatory
                 DESCRIPTION
                          "ONU type template Wan port config pppoe table."
                 ::= { nmsGponOnuTypeTemplateObj 15 }

             onuTypeTemplateWanPortConfigPppoeEntry OBJECT-TYPE
                 SYNTAX OnuTypeTemplateWanPortConfigPppoeEntry
                 ACCESS  not-accessible
                 STATUS  mandatory
                 DESCRIPTION
                          "ONU type template Wan port config pppoe table entry."
                 INDEX { onuTypeTemplateWanPortConfigPppoeTemplateIndex,  onuTypeTemplateWanPortConfigPppoePortIndex}
             ::= { onuTypeTemplateWanPortConfigPppoeTable 1 }

             OnuTypeTemplateWanPortConfigPppoeEntry ::=
                 SEQUENCE {
                     onuTypeTemplateWanPortConfigPppoeTemplateIndex
                         INTEGER,
                     onuTypeTemplateWanPortConfigPppoePortIndex 
                         INTEGER,
                     onuTypeTemplateWanPortConfigPppoeUsername
                         OCTET STRING,
                     onuTypeTemplateWanPortConfigPppoePassword
                         OCTET STRING,
                     onuTypeTemplateWanPortConfigPppoeRowStatus
                         RowStatus               
                 }

          onuTypeTemplateWanPortConfigPppoeTemplateIndex OBJECT-TYPE
              SYNTAX  INTEGER
              ACCESS  read-only
              STATUS  mandatory
              DESCRIPTION
                      "Index of the table, ONU port index."
              ::= { onuTypeTemplateWanPortConfigPppoeEntry 1 }
                 
          onuTypeTemplateWanPortConfigPppoePortIndex OBJECT-TYPE
              SYNTAX  INTEGER
              ACCESS  read-only
              STATUS  mandatory
              DESCRIPTION
                      "Index of the table, wan port index "
              ::= { onuTypeTemplateWanPortConfigPppoeEntry 2 }
              
          onuTypeTemplateWanPortConfigPppoeUsername OBJECT-TYPE
              SYNTAX  OCTET STRING              
              ACCESS  read-write
              STATUS  mandatory
              DESCRIPTION
                      "PPPOE Username(1-50bytes) "
              ::= { onuTypeTemplateWanPortConfigPppoeEntry 3 }
                 
          onuTypeTemplateWanPortConfigPppoePassword OBJECT-TYPE
              SYNTAX  OCTET STRING
              ACCESS  read-write
              STATUS  mandatory
              DESCRIPTION
                      "PPPOE Password(1-50bytes)"
              ::= { onuTypeTemplateWanPortConfigPppoeEntry 4 } 
              
          onuTypeTemplateWanPortConfigPppoeRowStatus OBJECT-TYPE
              SYNTAX  RowStatus
              ACCESS  read-create
              STATUS  mandatory
              DESCRIPTION
                      ""
              ::= { onuTypeTemplateWanPortConfigPppoeEntry 5 } 
              
              
--ONU类型模版Wan端口connecion name配置
             onuTypeTemplateWanPortConfigConnNameTable OBJECT-TYPE
                 SYNTAX  SEQUENCE OF OnuTypeTemplateWanPortConfigConnNameEntry
                 ACCESS  not-accessible
                 STATUS  mandatory
                 DESCRIPTION
                          "ONU type template Wan port config connection name table."
                 ::= { nmsGponOnuTypeTemplateObj 16 }

             onuTypeTemplateWanPortConfigConnNameEntry OBJECT-TYPE
                 SYNTAX OnuTypeTemplateWanPortConfigConnNameEntry
                 ACCESS  not-accessible
                 STATUS  mandatory
                 DESCRIPTION
                          "ONU type template Wan port config pppoe table entry."
                 INDEX { onuTypeTemplateWanPortConfigConnNameTemplateIndex,  onuTypeTemplateWanPortConfigConnNamePortIndex}
             ::= { onuTypeTemplateWanPortConfigConnNameTable 1 }

             OnuTypeTemplateWanPortConfigConnNameEntry ::=
                 SEQUENCE {
                     onuTypeTemplateWanPortConfigConnNameTemplateIndex
                         INTEGER,
                     onuTypeTemplateWanPortConfigConnNamePortIndex 
                         INTEGER,
                     onuTypeTemplateWanPortConfigConnName
                         OCTET STRING,
                     onuTypeTemplateWanPortConfigConnNameRowStatus
                         RowStatus               
                 }

          onuTypeTemplateWanPortConfigConnNameTemplateIndex OBJECT-TYPE
              SYNTAX  INTEGER
              ACCESS  read-only
              STATUS  mandatory
              DESCRIPTION
                      "Index of the table, ONU port index."
              ::= { onuTypeTemplateWanPortConfigConnNameEntry 1 }
                 
          onuTypeTemplateWanPortConfigConnNamePortIndex OBJECT-TYPE
              SYNTAX  INTEGER
              ACCESS  read-only
              STATUS  mandatory
              DESCRIPTION
                      "Index of the table, wan port index "
              ::= { onuTypeTemplateWanPortConfigConnNameEntry 2 }
              
          onuTypeTemplateWanPortConfigConnName OBJECT-TYPE
              SYNTAX  OCTET STRING              
              ACCESS  read-write
              STATUS  mandatory
              DESCRIPTION
                      "connection name(1-50bytes) "
              ::= { onuTypeTemplateWanPortConfigConnNameEntry 3 }
                 
          onuTypeTemplateWanPortConfigConnNameRowStatus OBJECT-TYPE
              SYNTAX  RowStatus
              ACCESS  read-create
              STATUS  mandatory
              DESCRIPTION
                      ""
              ::= { onuTypeTemplateWanPortConfigConnNameEntry 4 } 


--ONU类型模版Wan端口pppoe service name配置
             onuTypeTemplateWanPortConfigPppoeServcieNameTable OBJECT-TYPE
                 SYNTAX  SEQUENCE OF OnuTypeTemplateWanPortConfigPppoeServcieNameEntry
                 ACCESS  not-accessible
                 STATUS  mandatory
                 DESCRIPTION
                          "ONU type template Wan port config pppoe service name table."
                 ::= { nmsGponOnuTypeTemplateObj 17 }

             onuTypeTemplateWanPortConfigPppoeServcieNameEntry OBJECT-TYPE
                 SYNTAX OnuTypeTemplateWanPortConfigPppoeServcieNameEntry
                 ACCESS  not-accessible
                 STATUS  mandatory
                 DESCRIPTION
                          "ONU type template Wan port config pppoe service name table entry."
                 INDEX { onuTypeTemplateWanPortConfigPppoeServcieNameTemplateIndex,  onuTypeTemplateWanPortConfigPppoeServcieNamePortIndex}
             ::= { onuTypeTemplateWanPortConfigPppoeServcieNameTable 1 }

             OnuTypeTemplateWanPortConfigPppoeServcieNameEntry ::=
                 SEQUENCE {
                     onuTypeTemplateWanPortConfigPppoeServcieNameTemplateIndex
                         INTEGER,
                     onuTypeTemplateWanPortConfigPppoeServcieNamePortIndex 
                         INTEGER,
                     onuTypeTemplateWanPortConfigPppoeServcieName
                         OCTET STRING,
                     onuTypeTemplateWanPortConfigPppoeServcieNameRowStatus
                         RowStatus               
                 }

          onuTypeTemplateWanPortConfigPppoeServcieNameTemplateIndex OBJECT-TYPE
              SYNTAX  INTEGER
              ACCESS  read-only
              STATUS  mandatory
              DESCRIPTION
                      "Index of the table, ONU port index."
              ::= { onuTypeTemplateWanPortConfigPppoeServcieNameEntry 1 }
                 
          onuTypeTemplateWanPortConfigPppoeServcieNamePortIndex OBJECT-TYPE
              SYNTAX  INTEGER
              ACCESS  read-only
              STATUS  mandatory
              DESCRIPTION
                      "Index of the table, wan port index "
              ::= { onuTypeTemplateWanPortConfigPppoeServcieNameEntry 2 }
              
          onuTypeTemplateWanPortConfigPppoeServcieName OBJECT-TYPE
              SYNTAX  OCTET STRING              
              ACCESS  read-write
              STATUS  mandatory
              DESCRIPTION
                      "connection name(1-50bytes) "
              ::= { onuTypeTemplateWanPortConfigPppoeServcieNameEntry 3 }
                 
          onuTypeTemplateWanPortConfigPppoeServcieNameRowStatus OBJECT-TYPE
              SYNTAX  RowStatus
              ACCESS  read-create
              STATUS  mandatory
              DESCRIPTION
                      ""
              ::= { onuTypeTemplateWanPortConfigPppoeServcieNameEntry 4 } 
              
              
--ONU类型模版Wan端口Ipv6配置

             onuTypeTemplateWanPortConfigIpv6Table OBJECT-TYPE
                 SYNTAX  SEQUENCE OF OnuTypeTemplateWanPortConfigIpv6Entry
                 ACCESS  not-accessible
                 STATUS  mandatory
                 DESCRIPTION
                          "ONU type template Wan port config ipv6 table."
                 ::= { nmsGponOnuTypeTemplateObj 18 }

             onuTypeTemplateWanPortConfigIpv6Entry OBJECT-TYPE
                 SYNTAX OnuTypeTemplateWanPortConfigIpv6Entry
                 ACCESS  not-accessible
                 STATUS  mandatory
                 DESCRIPTION
                          "ONU type template Wan port config ipv6 table entry."
                 INDEX { onuTypeTemplateWanPortConfigIpv6TemplateIndex,  onuTypeTemplateWanPortConfigIpv6PortIndex}
             ::= { onuTypeTemplateWanPortConfigIpv6Table 1 }

             OnuTypeTemplateWanPortConfigIpv6Entry ::=
                 SEQUENCE {
                     onuTypeTemplateWanPortConfigIpv6TemplateIndex
                         INTEGER,
                     onuTypeTemplateWanPortConfigIpv6PortIndex 
                         INTEGER,
                     onuTypeTemplateWanPortConfigIpv6Address
                         InetAddressIPv6,
                     onuTypeTemplateWanPortConfigIpv6Mask
                         InetAddressIPv6,
                     onuTypeTemplateWanPortConfigIpv6Gateway 
                         InetAddressIPv6,
                     onuTypeTemplateWanPortConfigIpv6PriDns
                         InetAddressIPv6,
                     onuTypeTemplateWanPortConfigIpv6SecDns
                         InetAddressIPv6,
                     onuTypeTemplateWanPortConfigIpv6RowStatus
                         RowStatus               
                 }

          onuTypeTemplateWanPortConfigIpv6TemplateIndex OBJECT-TYPE
              SYNTAX  INTEGER
              ACCESS  read-only
              STATUS  mandatory
              DESCRIPTION
                      "Index of the table, ONU port index."
              ::= { onuTypeTemplateWanPortConfigIpv6Entry 1 }
                 
          onuTypeTemplateWanPortConfigIpv6PortIndex OBJECT-TYPE
              SYNTAX  INTEGER
              ACCESS  read-only
              STATUS  mandatory
              DESCRIPTION
                      "Index of the table, wan port index "
              ::= { onuTypeTemplateWanPortConfigIpv6Entry 2 }
              
          onuTypeTemplateWanPortConfigIpv6Address OBJECT-TYPE
              SYNTAX  InetAddressIPv6              
              ACCESS  read-write
              STATUS  mandatory
              DESCRIPTION
                      "Config IPv6 Address "
              ::= { onuTypeTemplateWanPortConfigIpv6Entry 3 }
                 
          onuTypeTemplateWanPortConfigIpv6Mask OBJECT-TYPE
              SYNTAX  InetAddressIPv6
              ACCESS  read-write
              STATUS  mandatory
              DESCRIPTION
                      "Config ipv6 Netmask "
              ::= { onuTypeTemplateWanPortConfigIpv6Entry 4 } 
              
          onuTypeTemplateWanPortConfigIpv6Gateway OBJECT-TYPE
              SYNTAX  InetAddressIPv6
              ACCESS  read-write
              STATUS  mandatory
              DESCRIPTION
                      "Config ipv6 Gateway "
              ::= { onuTypeTemplateWanPortConfigIpv6Entry 5 }
                 
          onuTypeTemplateWanPortConfigIpv6PriDns OBJECT-TYPE
              SYNTAX  InetAddressIPv6
              ACCESS  read-write
              STATUS  mandatory
              DESCRIPTION
                      "Config ipv6 Primary DNS "
              ::= { onuTypeTemplateWanPortConfigIpv6Entry 6 }
              
          onuTypeTemplateWanPortConfigIpv6SecDns OBJECT-TYPE
              SYNTAX  InetAddressIPv6           
              ACCESS  read-write
              STATUS  mandatory
              DESCRIPTION
                      "Config ipv6 Secondary DNS "
              ::= { onuTypeTemplateWanPortConfigIpv6Entry 7 }
              
          onuTypeTemplateWanPortConfigIpv6RowStatus OBJECT-TYPE
              SYNTAX  RowStatus
              ACCESS  read-create
              STATUS  mandatory
              DESCRIPTION
                      ""
              ::= { onuTypeTemplateWanPortConfigIpv6Entry 8 } 

-- ONU类型模版Voip端口配置表

             onuTypeTemplateVoipPortConfigTable OBJECT-TYPE
                 SYNTAX  SEQUENCE OF OnuTypeTemplateVoipPortConfigEntry
                 ACCESS  not-accessible
                 STATUS  mandatory
                 DESCRIPTION
                          "Onu type template Voip port config table."
                 ::= { nmsGponOnuTypeTemplateObj 19 }

             onuTypeTemplateVoipPortConfigEntry OBJECT-TYPE
                 SYNTAX OnuTypeTemplateVoipPortConfigEntry
                 ACCESS  not-accessible
                 STATUS  mandatory
                 DESCRIPTION
                          "Onu type template Voip port config table entry."
                 INDEX { onuTypeTemplateVoipPortConfigTemplateIndex, onuTypeTemplateVoipPortConfigVoipPortIndex }
             ::= { onuTypeTemplateVoipPortConfigTable 1 }

             OnuTypeTemplateVoipPortConfigEntry ::=
                 SEQUENCE {
                     onuTypeTemplateVoipPortConfigTemplateIndex
                         INTEGER,
                     onuTypeTemplateVoipPortConfigVoipPortIndex
                         INTEGER,
                     onuTypeTemplateVoipPortConfigVoipPortAdminState
                         INTEGER,
                     onuTypeTemplateVoipPortConfigVoipPortProfileID
                         INTEGER,
                     onuTypeTemplateVoipPortConfigSipDialPlanProfileID
                         INTEGER,
                     onuTypeTemplateVoipPortConfigVoipPortH248Tid
                         OCTET STRING,
                     onuTypeTemplateVoipPortConfigVoipPortH248Mid
                         OCTET STRING,
                     onuTypeTemplateVoipPortConfigVoipPortSipUserAor
                         OCTET STRING,
                     onuTypeTemplateVoipPortConfigVoipPortSipDispname
                         OCTET STRING,
                     onuTypeTemplateVoipPortConfigVoipPortSipUsername
                         OCTET STRING,
                     onuTypeTemplateVoipPortConfigVoipPortSipPassword
                         OCTET STRING,
                     onuTypeTemplateVoipPortConfigRowStatus
                         RowStatus
            }
                 
                 
          onuTypeTemplateVoipPortConfigTemplateIndex OBJECT-TYPE
              SYNTAX  INTEGER
              ACCESS  read-only
              STATUS  mandatory

              DESCRIPTION
                      ""
              ::= { onuTypeTemplateVoipPortConfigEntry 1 }


          onuTypeTemplateVoipPortConfigVoipPortIndex OBJECT-TYPE
              SYNTAX  INTEGER
              ACCESS  read-only
              STATUS  mandatory

              DESCRIPTION
                      ""
              ::= { onuTypeTemplateVoipPortConfigEntry 2 }

          onuTypeTemplateVoipPortConfigVoipPortAdminState OBJECT-TYPE
              SYNTAX  INTEGER{
                               no-shutdown(1),
                               shutdown(2)
                             }
              ACCESS  read-write
              STATUS  mandatory

              DESCRIPTION
                      "1-No shutdown  2-Shutdown "
              ::= { onuTypeTemplateVoipPortConfigEntry 3 }

          onuTypeTemplateVoipPortConfigVoipPortProfileID OBJECT-TYPE
              SYNTAX  INTEGER
              ACCESS  read-write
              STATUS  mandatory

              DESCRIPTION
                      "It points to the associated Voip Port profile. 0 means cancel profile config. 
                      Default value is 0."
              ::= { onuTypeTemplateVoipPortConfigEntry 4 }

          onuTypeTemplateVoipPortConfigSipDialPlanProfileID OBJECT-TYPE
              SYNTAX  INTEGER
              ACCESS  read-write
              STATUS  mandatory

              DESCRIPTION
                      "It points to the associated Voip Sip Dial Plan profile. 0 means cancel profile config. 
                      Default value is 0."
              ::= { onuTypeTemplateVoipPortConfigEntry 5 }

          onuTypeTemplateVoipPortConfigVoipPortH248Tid OBJECT-TYPE
              SYNTAX  OCTET STRING
              ACCESS  read-write
              STATUS  mandatory
              DESCRIPTION
                      "ONU voip port h248 tid."
              ::= { onuTypeTemplateVoipPortConfigEntry 6 }

          onuTypeTemplateVoipPortConfigVoipPortH248Mid OBJECT-TYPE
              SYNTAX  OCTET STRING
              ACCESS  read-write
              STATUS  mandatory
              DESCRIPTION
                      "ONU voip port h248 mid."
              ::= { onuTypeTemplateVoipPortConfigEntry 7 }

          onuTypeTemplateVoipPortConfigVoipPortSipUserAor OBJECT-TYPE
              SYNTAX  OCTET STRING
              ACCESS  read-write
              STATUS  mandatory
              DESCRIPTION
                      "ONU voip port Sip User Aor."
              ::= { onuTypeTemplateVoipPortConfigEntry 8 }

          onuTypeTemplateVoipPortConfigVoipPortSipDispname OBJECT-TYPE
              SYNTAX  OCTET STRING
              ACCESS  read-write
              STATUS  mandatory
              DESCRIPTION
                      "ONU voip port Sip Display name."
              ::= { onuTypeTemplateVoipPortConfigEntry 9 }

          onuTypeTemplateVoipPortConfigVoipPortSipUsername OBJECT-TYPE
              SYNTAX  OCTET STRING
              ACCESS  read-write
              STATUS  mandatory
              DESCRIPTION
                      "ONU voip port Sip User name."
              ::= { onuTypeTemplateVoipPortConfigEntry 10 }

          onuTypeTemplateVoipPortConfigVoipPortSipPassword OBJECT-TYPE
              SYNTAX  OCTET STRING
              ACCESS  read-write
              STATUS  mandatory
              DESCRIPTION
                      "ONU voip port Sip Password."
              ::= { onuTypeTemplateVoipPortConfigEntry 11 }

          onuTypeTemplateVoipPortConfigRowStatus OBJECT-TYPE
              SYNTAX  RowStatus
              ACCESS  read-create
              STATUS  mandatory

              DESCRIPTION
                      ""
              ::= { onuTypeTemplateVoipPortConfigEntry 12 }

--ONU类型模版Wifi端口通用配置

             onuTypeTemplateWifiConfigTable OBJECT-TYPE
                 SYNTAX  SEQUENCE OF OnuTypeTemplateWifiConfigEntry
                 ACCESS  not-accessible
                 STATUS  mandatory
                 DESCRIPTION
                          "ONU type template Wifi common config table."
                 ::= { nmsGponOnuTypeTemplateObj 20 }

             onuTypeTemplateWifiConfigEntry OBJECT-TYPE
                 SYNTAX OnuTypeTemplateWifiConfigEntry
                 ACCESS  not-accessible
                 STATUS  mandatory
                 DESCRIPTION
                          "ONU type template Wifi common config table entry."
                 INDEX { onuTypeTemplateWifiConfigTemplateIndex, onuTypeTemplateWifiConfigPortIndex }
             ::= { onuTypeTemplateWifiConfigTable 1 }

            OnuTypeTemplateWifiConfigEntry ::=
                 SEQUENCE {
                     onuTypeTemplateWifiConfigTemplateIndex
                         INTEGER,
                     onuTypeTemplateWifiConfigPortIndex 
                         INTEGER,
                     onuTypeTemplateWifiConfigTxpowerMode
                         INTEGER, 
                     onuTypeTemplateWifiConfigTxRate
                         INTEGER,
                     onuTypeTemplateWifiConfigCtrlband 
                         INTEGER,
                     onuTypeTemplateWifiConfigWlanEnable
                         INTEGER, 
                     onuTypeTemplateWifiConfigClear
                         BITS,
                     onuTypeTemplateWifiConfigRowStatus
                         RowStatus               
                 }

          onuTypeTemplateWifiConfigTemplateIndex OBJECT-TYPE
              SYNTAX  INTEGER
              ACCESS  read-only
              STATUS  mandatory
              DESCRIPTION
                      "Index of the table, ONU port index."
              ::= { onuTypeTemplateWifiConfigEntry 1 }
                 
          onuTypeTemplateWifiConfigPortIndex OBJECT-TYPE
              SYNTAX  INTEGER{
                        w_2_4_G_mode(1),
                        w_5G_mode(2)
                        }     
              ACCESS  read-only
              STATUS  mandatory
              DESCRIPTION
                      "Index of the table, 2.4G(1) or 5G(2) wifi port index "
              ::= { onuTypeTemplateWifiConfigEntry 2 }
              
          onuTypeTemplateWifiConfigTxpowerMode OBJECT-TYPE
              SYNTAX  INTEGER{
                        percent_15(1),
                        percent_35(2),
                        percent_50(3),
                        percent_70(4),
                        percent_100(5)
                        }
              ACCESS  read-write
              STATUS  mandatory
              DESCRIPTION
                      "wifi txpower mode"
              ::= { onuTypeTemplateWifiConfigEntry 3 }
              
          onuTypeTemplateWifiConfigTxRate OBJECT-TYPE
              SYNTAX  INTEGER            
              ACCESS  read-write
              STATUS  mandatory
              DESCRIPTION
                      "Wifi TxRate:
                        0--1M
                        1--2M
                        2--5.5M
                        3--6M
                        4--9M
                        5--11M
                        7--12M
                        8--18M
                        9--24M
                        10--36M
                        11--48M
                        12--54M
                        13-28 --MC0~MC15 (for 2.4G)
                        29-38 --NSS1-MCS0~NSS1-MCS9 (for 5G)
                        39-48 --NSS2-MCS0~NSS2-MCS9 (for 5G)"
              ::= { onuTypeTemplateWifiConfigEntry 4 }

          onuTypeTemplateWifiConfigCtrlband OBJECT-TYPE
              SYNTAX  INTEGER{
                        lower(0),
                        upper(1),
                        auto(2)
                        }              
              ACCESS  read-write
              STATUS  mandatory
              DESCRIPTION
                      "Wifi ctrlband:           
                                 0-lower(2.4G)；1-upper(2.4G)；2-auto(5G) "
              ::= { onuTypeTemplateWifiConfigEntry 5 }

          onuTypeTemplateWifiConfigWlanEnable OBJECT-TYPE
              SYNTAX  INTEGER{
                        enable(1),
                        disable(2)
                        }              
              ACCESS  read-write
              STATUS  mandatory
              DESCRIPTION
                      "WlanEnable:
                      1-Enable；2-Disable "
              ::= { onuTypeTemplateWifiConfigEntry 6 } 
              
          onuTypeTemplateWifiConfigClear OBJECT-TYPE
              SYNTAX  BITS{
                        chanInfoWidthMode(0),
                        txRate(1),
                        ctrlBand(2),
                        wlanEnable(3),
                        chanInfoTxPower(4)
                        }              
              ACCESS  read-write
              STATUS  mandatory
              DESCRIPTION
                      "Clear the Wifi mode config, every bit mean one config, 8 bits."
              ::= { onuTypeTemplateWifiConfigEntry 7 }              
              
          onuTypeTemplateWifiConfigRowStatus OBJECT-TYPE
              SYNTAX  RowStatus
              ACCESS  read-create
              STATUS  mandatory
              DESCRIPTION
                      ""
              ::= { onuTypeTemplateWifiConfigEntry 8 }
              
--Wifi channel配置

             onuTypeTemplateWifiConfigChannelTable OBJECT-TYPE
                 SYNTAX  SEQUENCE OF OnuTypeTemplateWifiConfigChannelEntry
                 ACCESS  not-accessible
                 STATUS  mandatory
                 DESCRIPTION
                          "ONU type template Wifi channel config table."
                 ::= { nmsGponOnuTypeTemplateObj 21 }

             onuTypeTemplateWifiConfigChannelEntry OBJECT-TYPE
                 SYNTAX OnuTypeTemplateWifiConfigChannelEntry
                 ACCESS  not-accessible
                 STATUS  mandatory
                 DESCRIPTION
                          "ONU type template Wifi channel config table entry."
                 INDEX { onuTypeTemplateWifiConfigChannelTemplateIndex,  onuTypeTemplateWifiConfigChannelPortIndex}
             ::= { onuTypeTemplateWifiConfigChannelTable 1 }

             OnuTypeTemplateWifiConfigChannelEntry ::=
                 SEQUENCE {
                     onuTypeTemplateWifiConfigChannelTemplateIndex
                         INTEGER,
                     onuTypeTemplateWifiConfigChannelPortIndex 
                         INTEGER,
                     onuTypeTemplateWifiConfigChannelWidth
                         INTEGER,
                     onuTypeTemplateWifiConfigChannelId
                         INTEGER,
                     onuTypeTemplateWifiConfigChannelRowStatus
                         RowStatus               
                 }

              onuTypeTemplateWifiConfigChannelTemplateIndex OBJECT-TYPE
                  SYNTAX  INTEGER
                  ACCESS  read-only
                  STATUS  mandatory
                  DESCRIPTION
                          "Index of the table, ONU port index."
                  ::= { onuTypeTemplateWifiConfigChannelEntry 1 }
                     
              onuTypeTemplateWifiConfigChannelPortIndex OBJECT-TYPE
                  SYNTAX  INTEGER{
                            w_2_4_G_mode(1),
                            w_5G_mode(2)
                            }     
                  ACCESS  read-only
                  STATUS  mandatory
                  DESCRIPTION
                          "Index of the table, ONU wifi 2.4G(1)/5G(2) mode index. "
                  ::= { onuTypeTemplateWifiConfigChannelEntry 2 }
                     
              onuTypeTemplateWifiConfigChannelWidth OBJECT-TYPE
                  SYNTAX  INTEGER{
                            w_20MHz(1),
                            w_40MHz(2)
                            w_20_40MHz(3),
                            w_80MHz(4)
                            }     
                  ACCESS  read-write
                  STATUS  mandatory
                  DESCRIPTION
                          "Wifi Channel Width:
                                1--20MHz for 2.4G/5G
                                2--40MHz for 2.4G/5G
                                3--20/40MHz for 2.4G
                                4--80MHz for 5G"
                  ::= { onuTypeTemplateWifiConfigChannelEntry 3 } 
                  
              onuTypeTemplateWifiConfigChannelId OBJECT-TYPE
                  SYNTAX  INTEGER
                  ACCESS  read-write
                  STATUS  mandatory
                  DESCRIPTION
                          "Wifi Channel Id:
                            Id:0      for auto choose channel id
                            Id:1-13   for 20MHz width for 2.4G
                            Id:5-13   for 40MHz or 20/40MHz width 2.4G
                            Id:36\40\44\48\52\56\60\64\149\153\157\161\165 for 5G 
                            And id 165 is only for 20Mhz(5G) channel width"
                  ::= { onuTypeTemplateWifiConfigChannelEntry 4 }
            
               onuTypeTemplateWifiConfigChannelRowStatus OBJECT-TYPE
                  SYNTAX  RowStatus
                  ACCESS  read-create
                  STATUS  mandatory
                  DESCRIPTION
                          ""
                  ::= { onuTypeTemplateWifiConfigChannelEntry 5 } 
              
--Wifi ssid 配置
             onuTypeTemplateWifiConfigSsidTable OBJECT-TYPE
                 SYNTAX  SEQUENCE OF OnuTypeTemplateWifiConfigSsidEntry
                 ACCESS  not-accessible
                 STATUS  mandatory
                 DESCRIPTION
                          "ONU type template Wifi ssid port config table."
                 ::= { nmsGponOnuTypeTemplateObj 22 }
             onuTypeTemplateWifiConfigSsidEntry OBJECT-TYPE
                 SYNTAX OnuTypeTemplateWifiConfigSsidEntry
                 ACCESS  not-accessible
                 STATUS  mandatory
                 DESCRIPTION
                          "ONU type template Wifi ssid config table entry."
                 INDEX { onuTypeTemplateWifiConfigSsidTemplateIndex,  onuTypeTemplateWifiConfigSsidPortIndex}
             ::= { onuTypeTemplateWifiConfigSsidTable 1 }
             
             OnuTypeTemplateWifiConfigSsidEntry ::=
                 SEQUENCE {
                     onuTypeTemplateWifiConfigSsidTemplateIndex
                         INTEGER,
                     onuTypeTemplateWifiConfigSsidPortIndex 
                         INTEGER,
                     onuTypeTemplateWifiConfigSsidAdmin
                         INTEGER,
                     onuTypeTemplateWifiConfigSsidbroadcastadmin
                         INTEGER,
                     onuTypeTemplateWifiConfigSsidMaxsta 
                         INTEGER,
                     onuTypeTemplateWifiConfigWlanStandard
                         INTEGER,
                     onuTypeTemplateWifiConfigSGI
                         INTEGER, 
                     onuTypeTemplateWifiConfigSsidClear
                         BITS,
                     onuTypeTemplateWifiConfigSsidRowStatus
                         RowStatus               
                 }

          onuTypeTemplateWifiConfigSsidTemplateIndex OBJECT-TYPE
              SYNTAX  INTEGER
              ACCESS  read-only
              STATUS  mandatory
              DESCRIPTION
                      "Index of the table, ONU port index."
              ::= { onuTypeTemplateWifiConfigSsidEntry 1 }
                 
          onuTypeTemplateWifiConfigSsidPortIndex OBJECT-TYPE
              SYNTAX  INTEGER
              ACCESS  read-only
              STATUS  mandatory
              DESCRIPTION
                      "Index of the table, ssid index "
              ::= { onuTypeTemplateWifiConfigSsidEntry 2 }
              
          onuTypeTemplateWifiConfigSsidAdmin OBJECT-TYPE
              SYNTAX  INTEGER{
                        enable(1),
                        disable(2)
                        }                    
              ACCESS  read-write
              STATUS  mandatory
              DESCRIPTION
                      "Ssid Admin:
                       1-Eable;2-Disable"
              ::= { onuTypeTemplateWifiConfigSsidEntry 3 }
                 
          onuTypeTemplateWifiConfigSsidbroadcastadmin OBJECT-TYPE
              SYNTAX  INTEGER{
                        enable(1),
                        disable(2)
                        }      
              ACCESS  read-write
              STATUS  mandatory
              DESCRIPTION
                      "Ssid Broadcast Admin:
                       1-Eable;2-Disable"
              ::= { onuTypeTemplateWifiConfigSsidEntry 4 } 
              
          onuTypeTemplateWifiConfigSsidMaxsta OBJECT-TYPE
              SYNTAX  INTEGER
              ACCESS  read-write
              STATUS  mandatory
              DESCRIPTION
                      "1-128 config ssid max user number, 
                       0-- max user number is not limited"
              ::= { onuTypeTemplateWifiConfigSsidEntry 5 }
                 
          onuTypeTemplateWifiConfigWlanStandard OBJECT-TYPE
              SYNTAX  INTEGER
              ACCESS  read-write
              STATUS  mandatory
              DESCRIPTION
                      "WlanStandard:
                      1--802.11b(2.4G)
                      2--802.11g(2.4G)
                      3--802.11n(2.4G)
                      4--802.11b+802.11g(2.4G)
                      5--802.11g+802.11n(2.4G)
                      6--802.11b+802.11g+802.11n(2.4G)
                      7--A(5G)
                      8--N(5G)
                      9--A+N(5G)
                      10--AC(5G)
                      11--N+AC(5G)
                      12--A+N+AC(5G)"
              ::= { onuTypeTemplateWifiConfigSsidEntry 6 }
              
          onuTypeTemplateWifiConfigSGI OBJECT-TYPE
              SYNTAX  INTEGER{
                        enable(1),
                        disable(2)
                        }               
              ACCESS  read-write
              STATUS  mandatory
              DESCRIPTION
                      "SGI:
                       1-Eable;2-Disable"
              ::= { onuTypeTemplateWifiConfigSsidEntry 7 }  
              
          onuTypeTemplateWifiConfigSsidClear OBJECT-TYPE
              SYNTAX  BITS{
                        ssidName(0),
                        ssidAdmin(1),
                        ssidBcstAdmin(2),
                        ssidMaxSta(3),
                        wlanStandard(4),
                        encryptMode(5),   
                        encryptKey(6),  
                        encryptSgi(7)
                        }               
              ACCESS  read-write
              STATUS  mandatory
              DESCRIPTION
                      "Clear the Wifi port config, every bit mean one config, 8 bits."
              ::= { onuTypeTemplateWifiConfigSsidEntry 8 }
              
          onuTypeTemplateWifiConfigSsidRowStatus OBJECT-TYPE
              SYNTAX  RowStatus
              ACCESS  read-create
              STATUS  mandatory
              DESCRIPTION
                      ""
              ::= { onuTypeTemplateWifiConfigSsidEntry 9 } 


--Wifi加密配置

             onuTypeTemplateWifiConfigSsidEncryptTable OBJECT-TYPE
                 SYNTAX  SEQUENCE OF OnuTypeTemplateWifiConfigSsidEncryptEntry
                 ACCESS  not-accessible
                 STATUS  mandatory
                 DESCRIPTION
                          "ONU type template Wifi encrypt config table."
                 ::= { nmsGponOnuTypeTemplateObj 23 }

             onuTypeTemplateWifiConfigSsidEncryptEntry OBJECT-TYPE
                 SYNTAX OnuTypeTemplateWifiConfigSsidEncryptEntry
                 ACCESS  not-accessible
                 STATUS  mandatory
                 DESCRIPTION
                          "ONU type template Wifi encrypt config table entry."
                 INDEX { onuTypeTemplateWifiConfigSsidEncryptTemplateIndex,  onuTypeTemplateWifiConfigSsidEncryptPortIndex}
             ::= { onuTypeTemplateWifiConfigSsidEncryptTable 1 }

             OnuTypeTemplateWifiConfigSsidEncryptEntry ::=
                 SEQUENCE {
                     onuTypeTemplateWifiConfigSsidEncryptTemplateIndex
                         INTEGER,
                     onuTypeTemplateWifiConfigSsidEncryptPortIndex 
                         INTEGER,
                     onuTypeTemplateWifiConfigSsidEncryptMode
                         INTEGER,
                     onuTypeTemplateWifiConfigSsidEncryptKey
                         OCTET STRING,
                     onuTypeTemplateWifiConfigSsidEncryptRowStatus
                         RowStatus               
                 }       

          onuTypeTemplateWifiConfigSsidEncryptTemplateIndex OBJECT-TYPE
              SYNTAX  INTEGER
              ACCESS  read-only
              STATUS  mandatory
              DESCRIPTION
                      "Index of the table, ONU port index."
              ::= { onuTypeTemplateWifiConfigSsidEncryptEntry 1 }
                 
          onuTypeTemplateWifiConfigSsidEncryptPortIndex OBJECT-TYPE
              SYNTAX  INTEGER
              ACCESS  read-only
              STATUS  mandatory
              DESCRIPTION
                      "Index of the table, wifi ssid index "
              ::= { onuTypeTemplateWifiConfigSsidEncryptEntry 2 }
              
          onuTypeTemplateWifiConfigSsidEncryptMode OBJECT-TYPE
              SYNTAX  INTEGER{
                        none(0),
                        wep(1),
                        wpa(2),
                        wpa2(3),
                        wpa_wpa2(4)
                        }               
              ACCESS  read-write
              STATUS  mandatory
              DESCRIPTION
                      "Encrypt Mode:
                       0--none
                       1--wep
                       2--wpa
                       3--wpa2
                       4--wpa_wpa2"
              ::= { onuTypeTemplateWifiConfigSsidEncryptEntry 3 }
                 
          onuTypeTemplateWifiConfigSsidEncryptKey OBJECT-TYPE
              SYNTAX  OCTET STRING
              ACCESS  read-write
              STATUS  mandatory
              DESCRIPTION
                      "wifi encrypt key (8-64 byte)"
              ::= { onuTypeTemplateWifiConfigSsidEncryptEntry 4 } 

          onuTypeTemplateWifiConfigSsidEncryptRowStatus OBJECT-TYPE
              SYNTAX  RowStatus
              ACCESS  read-create
              STATUS  mandatory
              DESCRIPTION
                      ""
              ::= { onuTypeTemplateWifiConfigSsidEncryptEntry 5} 


--Wifi ssid name配置

             onuTypeTemplateWifiConfigSsidNameTable OBJECT-TYPE
                 SYNTAX  SEQUENCE OF OnuTypeTemplateWifiConfigSsidNameEntry
                 ACCESS  not-accessible
                 STATUS  mandatory
                 DESCRIPTION
                          "ONU type template Wifi config ssid name table."
                 ::= { nmsGponOnuTypeTemplateObj 24 }

             onuTypeTemplateWifiConfigSsidNameEntry OBJECT-TYPE
                 SYNTAX OnuTypeTemplateWifiConfigSsidNameEntry
                 ACCESS  not-accessible
                 STATUS  mandatory
                 DESCRIPTION
                          "ONU type template Wifi config ssid name table entry."
                 INDEX { onuTypeTemplateWifiConfigSsidNameTemplateIndex,  onuTypeTemplateWifiConfigSsidNamePortIndex}
             ::= { onuTypeTemplateWifiConfigSsidNameTable 1 }

             OnuTypeTemplateWifiConfigSsidNameEntry ::=
                 SEQUENCE {
                     onuTypeTemplateWifiConfigSsidNameTemplateIndex
                         INTEGER,
                     onuTypeTemplateWifiConfigSsidNamePortIndex 
                         INTEGER,
                     onuTypeTemplateWifiConfigSsidName
                         OCTET STRING,
                     onuTypeTemplateWifiConfigSsidNameRowStatus
                         RowStatus               
                 }

          onuTypeTemplateWifiConfigSsidNameTemplateIndex OBJECT-TYPE
              SYNTAX  INTEGER
              ACCESS  read-only
              STATUS  mandatory
              DESCRIPTION
                      "Index of the table, ONU port index."
              ::= { onuTypeTemplateWifiConfigSsidNameEntry 1 }
                 
          onuTypeTemplateWifiConfigSsidNamePortIndex OBJECT-TYPE
              SYNTAX  INTEGER
              ACCESS  read-only
              STATUS  mandatory
              DESCRIPTION
                      "Index of the table, wifi ssid index "
              ::= { onuTypeTemplateWifiConfigSsidNameEntry 2 }
              
          onuTypeTemplateWifiConfigSsidName OBJECT-TYPE
              SYNTAX  OCTET STRING           
              ACCESS  read-write
              STATUS  mandatory
              DESCRIPTION
                      "config ssid name (1-32 byte) "
              ::= { onuTypeTemplateWifiConfigSsidNameEntry 3 }
                 
          onuTypeTemplateWifiConfigSsidNameRowStatus OBJECT-TYPE
              SYNTAX  RowStatus
              ACCESS  read-create
              STATUS  mandatory
              DESCRIPTION
                      ""
              ::= { onuTypeTemplateWifiConfigSsidNameEntry 4 } 
              
--ONU类型模版通用端口配置 
         onuTypeTemplateGeneralUniConfigTable OBJECT-TYPE
              SYNTAX  SEQUENCE OF OnuTypeTemplateGeneralUniConfigEntry
              ACCESS  not-accessible
              STATUS  mandatory
              DESCRIPTION
                      "ONU type template general uni config table."
             ::= { nmsGponOnuTypeTemplateObj 25 }

         onuTypeTemplateGeneralUniConfigEntry OBJECT-TYPE
             SYNTAX OnuTypeTemplateGeneralUniConfigEntry
             ACCESS  not-accessible
             STATUS  mandatory
             DESCRIPTION
                      "ONU type template general uni config table entry."
             INDEX { onuTypeTemplateGeneralUniConfigDeviceIndex,  onuTypeTemplateGeneralUniConfigPortIndex}
         ::= { onuTypeTemplateGeneralUniConfigTable 1 }

         OnuTypeTemplateGeneralUniConfigEntry ::=
             SEQUENCE {
                 onuTypeTemplateGeneralUniConfigTemplateIndex
                     INTEGER,
                 onuTypeTemplateGeneralUniConfigPortIndex 
                     INTEGER,
                 onuTypeTemplateGeneralUniConfigAdminState
                     INTEGER,
                 onuTypeTemplateGeneralUniConfigRowStatus
                     RowStatus
             }

          onuTypeTemplateGeneralUniConfigTemplateIndex OBJECT-TYPE
              SYNTAX  INTEGER
              ACCESS  read-only
              STATUS  mandatory
              DESCRIPTION
                      "Index of the template."
              ::= { onuTypeTemplateGeneralUniConfigEntry 1 }
                 
          onuTypeTemplateGeneralUniConfigPortIndex OBJECT-TYPE
              SYNTAX  INTEGER
              ACCESS  read-only
              STATUS  mandatory
              DESCRIPTION
                      "Index of the table, port index "
              ::= { onuTypeTemplateGeneralUniConfigEntry 2 }
              
          onuTypeTemplateGeneralUniConfigAdminState OBJECT-TYPE
              SYNTAX  INTEGER{
                        no-shutdown(1),
                        shutdown(2)
                        }              
              ACCESS  read-write
              STATUS  mandatory
              DESCRIPTION
                      "1-No shutdown  2-Shutdown "
              ::= { onuTypeTemplateGeneralUniConfigEntry 3 }
              
          onuTypeTemplateGeneralUniConfigRowStatus OBJECT-TYPE
              SYNTAX  RowStatus
              ACCESS  read-create
              STATUS  mandatory

              DESCRIPTION
                      ""
              ::= { onuTypeTemplateGeneralUniConfigEntry 4 } 

END
