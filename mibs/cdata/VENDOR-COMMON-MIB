--
-- VENDOR-COMMON-MIB.my
-- MIB generated by MG-SOFT Visual MIB Builder Version 6.0  Build 88
-- Tuesday, Dec 25, 2017 at 15:03:49
--

	VENDOR-COMMON-MIB DEFINITIONS ::= BEGIN
 
		IMPORTS
			enterprises, MODULE-IDENTITY, OBJECT-IDENTITY			
				FROM SNMPv2-SMI			
			TEXTUAL-CONVENTION			
				FROM SNMPv2-TC;
	
	
-- 1.3.6.1.4.1.34592
		vendor MODULE-IDENTITY 
			LAST-UPDATED "201005271056Z"		-- May 27, 2010 at 10:56 GMT
			ORGANIZATION 
				"vendor."
			CONTACT-INFO 
				" "
			DESCRIPTION 
				"vendor common mib module"
			::= { enterprises 34592 }

		
	
--
-- Textual conventions
--

		NscrtvPonExtDeviceIndex ::= TEXTUAL-CONVENTION
			STATUS current
			DESCRIPTION 
				"olt/onu Device Index 
				Four byte,include:         
				         Olt device-8bit OLT Card-8bit Pon port-8bit OnuNUM-8bit
				         Note: 
				   ----        
				   1. OLT device must not be 0.        
				   2. Card here shall confirm the last byte definition of NscrtvPonExtCardIndex
				      to indicate the main-slot and sub-slot index.         
				   3. Pon port must not be 0.
				   4. The useful ONU logical ID MUST never be set to 0, where NUM of 0 has
				      another meaning, to indicate that the ONU logical ID is meaningless,
				      or said to not applied.
				           
				   Usage guide:
				   -----------        
				   This TC could be used for OLT SNI, OLT PON port, OLT ONU ID
				   OLT device, trunk.         
				   If the refered MIB object does not have clear definition,
				   refer to the following:
				   Applied Obj  - Descriptions of Index
				   ------------------------------------------------------------------
				   OLT Pon Port - OnuNum shall be set to 0,
				   OLT SNI    - Same as OLT Pon Port         
				   OLT onu ID   - Set OnuNUM to corresponding ONU logical ID         
				   OLT device   - Set card, pon port and OnuNUM to 0
				   Trunk    - Card to 0x3F, pon port to trunk ID, OnuNUM to 0
				            Olt device to corresponding ONU device       
				        "
			SYNTAX Unsigned32

		NscrtvPonExtCardIndex ::= TEXTUAL-CONVENTION
			STATUS current
			DESCRIPTION 
				"Card Index
				For easy presenting the chassis view by NMS, bCardIndex shall be formatted
				in a following manner:                        
				Four bytes of INTEGER, from the most significant byte to the least significant bytes
				-----------------------------------------------------------------------------
				Reserved byte Reserved byte   Reserved byte Sub-slot 2-bit Main-slot 6-bit        
				Notes:
				-----         
				1. Reserved bytes shall be set to 0.        
				2. The main-slot shall be started from 1, and shall be in a consecutive manner,
				   for all slots, including service slots, control slots, switch slots, power
				   slots,FAN slots, etc.For example, 1, 2, 3          
				3. The sub-slot shall be started from 1, and shall be in a consecutive manner.
				   For example, 1, 2. If no sub-slot concept of a main-slot, set to 0.        
				4. For fixed device, if no slot concept, NE shall set both main-slot and sub-slot
				   to 0, to indicate this is meaningless. For modulized device, they MUST not be
				   set to 0.This definition shall applied to both OLT and ONU.        
				5. For trunk, since there is no slot concept, set main-slot to all-1 and sub-slot
				   to 0. This definition shall applied to both OLT and ONU.
				
				For example, 
				0x00 00 00 0A, represents main-slot 10, no sub-slot
				0x00 00 00 42, represents main-slot 2, sub-slot 1
				0x00 00 00 3F, represents a trunk
				"
			SYNTAX Unsigned32

		NscrtvPonPortIndex ::= TEXTUAL-CONVENTION
			STATUS current
			DESCRIPTION 
				"Port Index        
				The device port number shall start from 1. Nunber 0 had specific meaning, stands
				for portIndex is meaningless, for the situation defined.
				"
			SYNTAX Unsigned32 (0..255)

		NscrtvPonExtEtherType ::= TEXTUAL-CONVENTION
			STATUS current
			DESCRIPTION 
				"Description."
			SYNTAX INTEGER
				{
				ipv4(1),
				ipv6(2),
				pppoe(3)
				}

		NscrtvPonExtAdminStatus ::= TEXTUAL-CONVENTION
			STATUS current
			DESCRIPTION 
				"Description."
			SYNTAX INTEGER
				{
				disable(0),
				enable(1)
				}

		NscrtvPonExtOnuOnlineState ::= TEXTUAL-CONVENTION
			STATUS current
			DESCRIPTION 
				"Description."
			SYNTAX INTEGER
				{
				offline(0),
				online(1)
				}

		NscrtvPonExtVlanTagAction ::= TEXTUAL-CONVENTION
			STATUS current
			DESCRIPTION 
				"Description."
			SYNTAX INTEGER
				{
				default(0),
				translate(1),
				translate-and-add(2),
				add-double(3),
				transparent(4)
				}

		NscrtvPonExtPerfStat ::= TEXTUAL-CONVENTION
			STATUS current
			DESCRIPTION 
				"Description."
			SYNTAX INTEGER
				{
				disable(0),
				enable(1)
				}

		NscrtvPonExtAutoMode ::= TEXTUAL-CONVENTION
			STATUS current
			DESCRIPTION 
				"Description."
			SYNTAX INTEGER
				{
				auto(0),
				manual(1)
				}

		NscrtvPonExtCurPerfStatClear ::= TEXTUAL-CONVENTION
			STATUS current
			DESCRIPTION 
				"Description."
			SYNTAX INTEGER
				{
				no-clear(0),
				clear(1)
				}
	
	
				EponDeviceIndex ::= TEXTUAL-CONVENTION
			STATUS current
			DESCRIPTION 
				""
			SYNTAX Unsigned32


		OperSwitch ::= TEXTUAL-CONVENTION
			STATUS current
			DESCRIPTION 
				"Device function operation switch type"
			SYNTAX INTEGER
				{
				enable(1),
				disable(2)
				}

		DeviceStatus ::= TEXTUAL-CONVENTION
			STATUS current
			DESCRIPTION 
				"Device work status type. One device or dummy device may
				have following five work status:
				notPresent(1): the device is not present (not installed)
				offline(2):the device is present,but can not be communicated (or failed to get its info)
				online(3):the device is present and can be communicated
				normal(4):the device is online and work well
				abnormal(5): the device is online but work abnormal for some reason"
			SYNTAX INTEGER
				{
				notPresent(1),
				offline(2),
				online(3),
				normal(4),
				abnormal(5)
				}

		DataDirection ::= TEXTUAL-CONVENTION
			STATUS current
			DESCRIPTION 
				"A data channel normally have two direction, up and down"
			SYNTAX INTEGER
				{
				upstream(1),
				downstream(2)
				}

		DeviceOperation ::= TEXTUAL-CONVENTION
			STATUS current
			DESCRIPTION 
				"This type defines an operate action aggregate"
			SYNTAX INTEGER
				{
				reset(2),
				default(3),
				saveConfig(4),
				restore(5),
				delete(6)
				}

		LedStatus ::= TEXTUAL-CONVENTION
			STATUS current
			DESCRIPTION 
				"Led status"
			SYNTAX INTEGER
				{
				on(1),
				off(2),
				blink(3)
				}

		DeviceType ::= TEXTUAL-CONVENTION
			STATUS current
			DESCRIPTION 
				"Device type convention. Define all PBB device type value.
				
				----------------------------------
				| family | series | class | type |
				----------------------------------
				   8b        8b      8b      8b
				
				refer to document <pducuct type defines>"
			SYNTAX INTEGER
				{
				epon(16842752),
				chassis(16843009),
				olt(16843265),
				pon(16843521),
				pon1(16909057),
				epon1u(17105153),
				olt1(17105409),
				pon2(17105665),
				onu4db(16974081),
				onu4db1(16974082),
				onu4db2(16974083),
				onu8db(16974084),
				onu4d(16974085),
				onu1d(16974086),
				onu1dg(16974087),
				onu2dg(16974088),
				onu2dgm(16974095),
				onu4dgm(16974094),
				onu4dp(16974089),
				onu3dm(16974090),
				onu4d1(16974091),
				onu2dm(16974092),
				onu4d2p(16974337),
				onu4d2pp(16974338),
				onu4d1r(16974593),
				onu4d1rp(16974594),
				onu4d2p1r(16974849),
				onu4d2p1r1(17040129),
				onu4d2p1rp(16974850),
				onu24d(17039617)
				}

	
--
-- Node definitions
--
	
-- 1.3.6.1.4.1.34592.1
		ipProduct OBJECT-IDENTITY
			STATUS current
			DESCRIPTION 
				"Defines the base identifier containing the definition of ip products line.
				"
			::= { vendor 1 }

		
-- 1.3.6.1.4.1.34592.1.1
		mediaConverter OBJECT-IDENTITY
			STATUS current
			DESCRIPTION 
				"Defines the base identifier for the subtree
				supported by media converter line products.
				"
			::= { ipProduct 1 }

		
-- 1.3.6.1.4.1.34592.1.2
		switch OBJECT-IDENTITY
			STATUS current
			DESCRIPTION 
				"Defines the base identifier for the subtree
				supported by smartCPE Switch line products.
				"
			::= { ipProduct 2 }

		
-- 1.3.6.1.4.1.34592.1.3
		pon OBJECT-IDENTITY
			STATUS current
			DESCRIPTION 
				" "
			::= { ipProduct 3 }

		
-- 1.3.6.1.4.1.34592.1.4
		eoc OBJECT-IDENTITY
			STATUS current
			DESCRIPTION 
				" "
			::= { ipProduct 4 }

		
	
	END

--
-- EPON-EOC-MIB.my
--
