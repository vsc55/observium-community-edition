-- *******************************************************************
-- QTECH-IP-PRIVATE-MIB.mib : Qtech AC IP MIB file
-- May 2010, humin
--
-- Copyright (c) 2009 by Qtech Networks Co.,Ltd.
-- All rights reserved.
-- *******************************************************************
--
QTECH-IP-PRIVATE-MIB DEFINITIONS ::= BEGIN

IMPORTS
        IpAddress,
        OBJECT-TYPE,
        MODULE-IDENTITY,
        NOTIFICATION-TYPE,
        Counter32
                FROM SNMPv2-SMI
        MacAddress,
        DisplayString,
        RowStatus
                FROM SNMPv2-TC
        MODULE-COMPLIANCE,
        NOTIFICATION-GROUP,
        OBJECT-GROUP
                FROM SNMPv2-CONF
        qtechMgmt
                FROM QTECH-SMI; 
                
qtechIPPrivateMgmt MODULE-IDENTITY
    LAST-UPDATED "200909180000Z"
    ORGANIZATION "Qtech Networks Co.,Ltd."
    CONTACT-INFO
        " 
    Tel: 4008-111-000

    E-mail: service@qtech.com.cn"
    DESCRIPTION
        "This module defines ac management mibs."
    REVISION      "200909180000Z"
    DESCRIPTION
        "Initial version of this MIB module."
    ::= { qtechMgmt 73}

-- ******** define the notify nodes *************
qtechIPPrivateAcNotificationsMIBObjects OBJECT IDENTIFIER ::= { qtechIPPrivateMgmt 1 }
qtechIPPrivateAcNtfObjects              OBJECT IDENTIFIER ::= { qtechIPPrivateAcNotificationsMIBObjects 1 }
qtechIPPrivateAcNotifications           OBJECT IDENTIFIER ::= { qtechIPPrivateAcNotificationsMIBObjects 2 }

-- ****************************************
--
--               Notify nodes
--
-- ****************************************
qtechIPPrivateAcNotifyIpv4AddressChangeType OBJECT-TYPE
    SYNTAX      INTEGER
    MAX-ACCESS  accessible-for-notify
    STATUS      current
    DESCRIPTION
        "Represents the AC Ipv4 address change operation, 0-del,1-add."
    ::= { qtechIPPrivateAcNtfObjects 1 }

qtechIPPrivateAcNotifyIpv4ChangeAddress OBJECT-TYPE
    SYNTAX      IpAddress
    MAX-ACCESS  accessible-for-notify
    STATUS      current
    DESCRIPTION
        "Represents the AC Ipv4 address which is changing."
    ::= { qtechIPPrivateAcNtfObjects 2 }

qtechIPPrivateAcNotifyIpv4ChangeAddressMask OBJECT-TYPE
    SYNTAX      IpAddress
    MAX-ACCESS  accessible-for-notify
    STATUS      current
    DESCRIPTION
        "Represents the AC Ipv4 address's mask which is changing."
    ::= { qtechIPPrivateAcNtfObjects 3 }

qtechIPPrivateAcNotifyIpv4ChangeIfIndex OBJECT-TYPE
    SYNTAX      INTEGER
    MAX-ACCESS  accessible-for-notify
    STATUS      current
    DESCRIPTION
        "Represents the AC Ipv4 address change on which interface."
    ::= { qtechIPPrivateAcNtfObjects 4 }

qtechIPPrivateAcNotifyChangeIpv4AddressAlarm NOTIFICATION-TYPE
    OBJECTS     {
                  qtechIPPrivateAcNotifyIpv4AddressChangeType,
                  qtechIPPrivateAcNotifyIpv4ChangeAddress,
                  qtechIPPrivateAcNotifyIpv4ChangeAddressMask,
                  qtechIPPrivateAcNotifyIpv4ChangeIfIndex
                }
    STATUS      current
    DESCRIPTION
        "This notification is sent by the AC when an AC's Ipv4 address is changed."
    ::= { qtechIPPrivateAcNotifications 1 }

--********************************************************************
--                                                                  **
--                ac query ap's ip information	                    **
--                                                                  **
--********************************************************************    
qtechIPPrivateAcQueryApMIBObject OBJECT IDENTIFIER ::= { qtechIPPrivateAcNotificationsMIBObjects 3 }
qtechIPPrivateAcQueryApInfo      OBJECT IDENTIFIER ::= { qtechIPPrivateAcQueryApMIBObject 1}

--********************************************************************
--                                                                  **
--            table about ac query ap's ip information              **
--                                                                  **
--******************************************************************** 
qtechIPPrivateAcQueryApMIBTable OBJECT-TYPE
    SYNTAX  SEQUENCE OF QtechIPPrivateApInfoEntry
    MAX-ACCESS  not-accessible
    STATUS  current
    DESCRIPTION
            "The Ap IP information."
    ::= { qtechIPPrivateAcQueryApInfo 1 }

qtechIPPrivateApInfoEntry OBJECT-TYPE
    SYNTAX  QtechIPPrivateApInfoEntry
    MAX-ACCESS  not-accessible
    STATUS  current
    DESCRIPTION
        "Get the Ap IP information."
    INDEX   { qtechIPPrivateAcApMacAddr,
              qtechIPPrivateAcApIp}
    ::= { qtechIPPrivateAcQueryApMIBTable 1 }

QtechIPPrivateApInfoEntry ::=
    SEQUENCE {
        qtechIPPrivateAcApMacAddr                 MacAddress,
        qtechIPPrivateAcApIp                      IpAddress,
        qtechIPPrivateAcApMask                    IpAddress,
        qtechIPPrivateAcApGateway                 IpAddress						
    }

qtechIPPrivateAcApMacAddr OBJECT-TYPE
    SYNTAX  MacAddress
    MAX-ACCESS  read-only
    STATUS  current
    DESCRIPTION
            "The AP's ethernet mac address."
    ::= { qtechIPPrivateApInfoEntry 1}
    
qtechIPPrivateAcApIp OBJECT-TYPE
    SYNTAX  IpAddress
    MAX-ACCESS  read-only
    STATUS  current
    DESCRIPTION
        "The AP's IP address."
    ::= { qtechIPPrivateApInfoEntry 2}
		
qtechIPPrivateAcApMask OBJECT-TYPE
    SYNTAX  IpAddress	   
    MAX-ACCESS  read-only
    STATUS  current
    DESCRIPTION
    	"The AP's MASK address."
    ::= { qtechIPPrivateApInfoEntry 3}				
    
qtechIPPrivateAcApGateway OBJECT-TYPE
    SYNTAX  IpAddress	   
    MAX-ACCESS  read-only
    STATUS  current
    DESCRIPTION
    	"The AP's Gateway address."
    ::= { qtechIPPrivateApInfoEntry 4}


--********************************************************************
--                                                                  **
--           conformance information                                **
--                                                                  **
--********************************************************************
qtechIPPrivateMIBConformance OBJECT IDENTIFIER ::= { qtechIPPrivateMgmt 2 }
qtechIPPrivateMIBCompliances OBJECT IDENTIFIER ::= { qtechIPPrivateMIBConformance 1 }
qtechIPPrivateMIBGroups      OBJECT IDENTIFIER ::= { qtechIPPrivateMIBConformance 2 }


--********************************************************************
--                                                                  **
--           compliance statements                                  **
--                                                                  **
--********************************************************************
-- qtechIPPrivateMIBCompliance MODULE-COMPLIANCE
--        STATUS  current
--        DESCRIPTION
--                "The compliance statement for entities which implement
--                the Qtech Ac Manager Ac"
--        MODULE
--                MANDATORY-GROUPS { qtechAcIPPrivateMIBGroup, qtechAcIPPrivateTrapGroup }
--        ::= { qtechIPPrivateMIBCompliances 1 }
        

--********************************************************************
--                                                                  **
--           units of conformance                                   **
--                                                                  **
--********************************************************************
qtechIPPrivateMIBGroup OBJECT-GROUP
        OBJECTS {
            qtechIPPrivateAcNotifyIpv4AddressChangeType,
            qtechIPPrivateAcNotifyIpv4ChangeAddress,
            qtechIPPrivateAcNotifyIpv4ChangeAddressMask,
            qtechIPPrivateAcNotifyIpv4ChangeIfIndex,
            qtechIPPrivateAcApMacAddr,
            qtechIPPrivateAcApIp,
            qtechIPPrivateAcApMask,
            qtechIPPrivateAcApGateway 
        }
        STATUS  current
        DESCRIPTION
                "A collection of objects providing ac manager (echo) ability to a
                Qtech agent."
        ::= { qtechIPPrivateMIBGroups 1 }

qtechIPPrivateTrapGroup NOTIFICATION-GROUP
    NOTIFICATIONS {
        qtechIPPrivateAcNotifyChangeIpv4AddressAlarm
    }
    STATUS  current
    DESCRIPTION
        "A collection of traps providing ac manager (echo) ability to a
         Qtech agent."
    ::= { qtechIPPrivateMIBGroups 2 }
    
END
