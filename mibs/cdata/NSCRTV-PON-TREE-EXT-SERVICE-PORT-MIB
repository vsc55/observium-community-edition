--
-- NSCRTV-PON-TREE-EXT-SERVICE-PORT-MIB.my
-- MIB generated by MG-SOFT Visual MIB Builder Version 6.0  Build 88
-- Friday, September 10, 2021 at 18:02:37
--

	NSCRTV-PON-TREE-EXT-SERVICE-PORT-MIB DEFINITIONS ::= BEGIN
 
		IMPORTS
			Integer32, Unsigned32, Counter64, OBJECT-TYPE, MODULE-IDENTITY			
				FROM SNMPv2-SMI			
			RowStatus			
				FROM SNMPv2-TC			
			pon, NscrtvPonExtDeviceIndex, NscrtvPonExtCardIndex, NscrtvPonExtEtherType, NscrtvPonExtAdminStatus, 
			NscrtvPonExtOnuOnlineState, NscrtvPonExtVlanTagAction, NscrtvPonExtPerfStat, NscrtvPonExtAutoMode, NscrtvPonExtCurPerfStatClear			
				FROM VENDOR-COMMON-MIB;
	
	
		-- 1.3.6.1.4.1.34592.1.3.100
		nscrtvPonTreeExt MODULE-IDENTITY 
			LAST-UPDATED "201706051636Z"		-- June 05, 2017 at 16:36 GMT
			ORGANIZATION 
				"Organization."
			CONTACT-INFO 
				"Contact-info."
			DESCRIPTION 
				"Description."
			::= { pon 100 }

		
	
	
--
-- Node definitions
--
	
		-- 1.3.6.1.4.1.34592.1.3.100.9
		servicePortObjects OBJECT IDENTIFIER ::= { nscrtvPonTreeExt 9 }

		
		-- 1.3.6.1.4.1.34592.1.3.100.9.1
		servicePortGlobalInfoTable OBJECT-TYPE
			SYNTAX SEQUENCE OF ServicePortGlobalInfoEntry
			MAX-ACCESS not-accessible
			STATUS current
			DESCRIPTION
				"业务虚端口全局信息表"
			::= { servicePortObjects 1 }

		
		-- 1.3.6.1.4.1.34592.1.3.100.9.1.1
		servicePortGlobalInfoEntry OBJECT-TYPE
			SYNTAX ServicePortGlobalInfoEntry
			MAX-ACCESS not-accessible
			STATUS current
			DESCRIPTION
				"Description."
			INDEX { servicePortGlobalInfoDeviceIndex, servicePortGlobalInfoCardIndex }
			::= { servicePortGlobalInfoTable 1 }

		
		ServicePortGlobalInfoEntry ::=
			SEQUENCE { 
				servicePortGlobalInfoDeviceIndex
					NscrtvPonExtDeviceIndex,
				servicePortGlobalInfoCardIndex
					NscrtvPonExtCardIndex,
				servicePortCfgInfoMaxId
					Unsigned32,
				servicePortGlobalInfoMaxSupportNumber
					Unsigned32,
				servicePortGlobalInfoCreatedNumber
					Unsigned32,
				servicePortAllStatsSwitch
					INTEGER
			 }

		-- 1.3.6.1.4.1.34592.1.3.100.9.1.1.1
		servicePortGlobalInfoDeviceIndex OBJECT-TYPE
			SYNTAX NscrtvPonExtDeviceIndex
			MAX-ACCESS not-accessible
			STATUS current
			DESCRIPTION
				"OLT设备索引号     
				一个OLT节点可以由多台OLT设备组成。节点内的每台OLT设备由OLT设备索引号唯一标识"
			::= { servicePortGlobalInfoEntry 1 }

		
		-- 1.3.6.1.4.1.34592.1.3.100.9.1.1.2
		servicePortGlobalInfoCardIndex OBJECT-TYPE
			SYNTAX NscrtvPonExtCardIndex
			MAX-ACCESS not-accessible
			STATUS current
			DESCRIPTION
				"板卡索引号"
			::= { servicePortGlobalInfoEntry 2 }

		
		-- 1.3.6.1.4.1.34592.1.3.100.9.1.1.3
		servicePortCfgInfoMaxId OBJECT-TYPE
			SYNTAX Unsigned32
			MAX-ACCESS read-only
			STATUS current
			DESCRIPTION
				"当前系统最大业务虚端口编号"
			::= { servicePortGlobalInfoEntry 3 }

		
		-- 1.3.6.1.4.1.34592.1.3.100.9.1.1.4
		servicePortGlobalInfoMaxSupportNumber OBJECT-TYPE
			SYNTAX Unsigned32
			MAX-ACCESS read-only
			STATUS current
			DESCRIPTION
				"当前系统最大支持的业务虚端口个数"
			::= { servicePortGlobalInfoEntry 4 }

		
		-- 1.3.6.1.4.1.34592.1.3.100.9.1.1.5
		servicePortGlobalInfoCreatedNumber OBJECT-TYPE
			SYNTAX Unsigned32
			MAX-ACCESS read-only
			STATUS current
			DESCRIPTION
				"当前系统已创建的业务虚端口个数"
			::= { servicePortGlobalInfoEntry 5 }

		
		-- 1.3.6.1.4.1.34592.1.3.100.9.1.1.6
		servicePortAllStatsSwitch OBJECT-TYPE
			SYNTAX INTEGER
				{
				disable(0),
				enable(1)
				}
			MAX-ACCESS read-write
			STATUS current
			DESCRIPTION
				"Description."
			::= { servicePortGlobalInfoEntry 6 }

		
		-- 1.3.6.1.4.1.34592.1.3.100.9.2
		servicePortCfgInfoTable OBJECT-TYPE
			SYNTAX SEQUENCE OF ServicePortCfgInfoEntry
			MAX-ACCESS not-accessible
			STATUS current
			DESCRIPTION
				"业务虚端口配置信息表"
			::= { servicePortObjects 2 }

		
		-- 1.3.6.1.4.1.34592.1.3.100.9.2.1
		servicePortCfgInfoEntry OBJECT-TYPE
			SYNTAX ServicePortCfgInfoEntry
			MAX-ACCESS not-accessible
			STATUS current
			DESCRIPTION
				"Description."
			INDEX { servicePortCfgInfoDeviceIndex, servicePortCfgInfoCardIndex, servicePortCfgInfoIndex }
			::= { servicePortCfgInfoTable 1 }

		
		ServicePortCfgInfoEntry ::=
			SEQUENCE { 
				servicePortCfgInfoDeviceIndex
					NscrtvPonExtDeviceIndex,
				servicePortCfgInfoCardIndex
					NscrtvPonExtCardIndex,
				servicePortCfgInfoIndex
					Unsigned32,
				servicePortCfgInfoSvlanId
					Unsigned32,
				servicePortCfgInfoPonPortId
					Unsigned32,
				servicePortCfgInfoOnuId
					Unsigned32,
				servicePortCfgInfoGemId
					Unsigned32,
				servicePortCfgInfoUserVlanId
					Unsigned32,
				servicePortCfgInfoUserVlanPri
					Unsigned32,
				servicePortCfgInfoEhterType
					NscrtvPonExtEtherType,
				servicePortCfgInfoUpTrafficProfileId
					Unsigned32,
				servicePortCfgInfoDownTrafficProfileId
					Unsigned32,
				servicePortCfgInfoAdminStatus
					NscrtvPonExtAdminStatus,
				servicePortCfgInfoOnuOnlineState
					NscrtvPonExtOnuOnlineState,
				servicePortCfgInfoVlanTagAction
					NscrtvPonExtVlanTagAction,
				servicePortCfgInfoVlanInnerVid
					Unsigned32,
				servicePortCfgInfoVlanInnerPri
					Unsigned32,
				servicePortCfgInfoDescription
					OCTET STRING,
				servicePortCfgInfoPerfStat
					NscrtvPonExtPerfStat,
				servicePortCfgInfoRowStatus
					RowStatus
			 }

		-- 1.3.6.1.4.1.34592.1.3.100.9.2.1.1
		servicePortCfgInfoDeviceIndex OBJECT-TYPE
			SYNTAX NscrtvPonExtDeviceIndex
			MAX-ACCESS not-accessible
			STATUS current
			DESCRIPTION
				"OLT设备索引号     
				一个OLT节点可以由多台OLT设备组成。节点内的每台OLT设备由OLT设备索引号唯一标识"
			::= { servicePortCfgInfoEntry 1 }

		
		-- 1.3.6.1.4.1.34592.1.3.100.9.2.1.2
		servicePortCfgInfoCardIndex OBJECT-TYPE
			SYNTAX NscrtvPonExtCardIndex
			MAX-ACCESS not-accessible
			STATUS current
			DESCRIPTION
				"板卡索引号"
			::= { servicePortCfgInfoEntry 2 }

		
		-- 1.3.6.1.4.1.34592.1.3.100.9.2.1.3
		servicePortCfgInfoIndex OBJECT-TYPE
			SYNTAX Unsigned32
			MAX-ACCESS not-accessible
			STATUS current
			DESCRIPTION
				"业务虚端口索引号"
			::= { servicePortCfgInfoEntry 3 }

		
		-- 1.3.6.1.4.1.34592.1.3.100.9.2.1.4
		servicePortCfgInfoSvlanId OBJECT-TYPE
			SYNTAX Unsigned32 (0..4094)
			MAX-ACCESS read-create
			STATUS current
			DESCRIPTION
				"上联口VLAN号
				范围1~4094"
			::= { servicePortCfgInfoEntry 4 }

		
		-- 1.3.6.1.4.1.34592.1.3.100.9.2.1.5
		servicePortCfgInfoPonPortId OBJECT-TYPE
			SYNTAX Unsigned32 (0..63)
			MAX-ACCESS read-create
			STATUS current
			DESCRIPTION
				"PON端口号(lport)
				范围0-63"
			::= { servicePortCfgInfoEntry 5 }

		
		-- 1.3.6.1.4.1.34592.1.3.100.9.2.1.6
		servicePortCfgInfoOnuId OBJECT-TYPE
			SYNTAX Unsigned32 (1..128)
			MAX-ACCESS read-create
			STATUS current
			DESCRIPTION
				"ONU号
				范围1~128"
			::= { servicePortCfgInfoEntry 6 }

		
		-- 1.3.6.1.4.1.34592.1.3.100.9.2.1.7
		servicePortCfgInfoGemId OBJECT-TYPE
			SYNTAX Unsigned32 (1..30)
			MAX-ACCESS read-create
			STATUS current
			DESCRIPTION
				"GEM号
				范围1~30"
			::= { servicePortCfgInfoEntry 7 }

		
		-- 1.3.6.1.4.1.34592.1.3.100.9.2.1.8
		servicePortCfgInfoUserVlanId OBJECT-TYPE
			SYNTAX Unsigned32 (1..4094)
			MAX-ACCESS read-create
			STATUS current
			DESCRIPTION
				"用户VLAN号
				范围1~4094"
			::= { servicePortCfgInfoEntry 8 }

		
		-- 1.3.6.1.4.1.34592.1.3.100.9.2.1.9
		servicePortCfgInfoUserVlanPri OBJECT-TYPE
			SYNTAX Unsigned32 (0..7)
			MAX-ACCESS read-create
			STATUS current
			DESCRIPTION
				"用户VLAN优先级
				范围0~7"
			::= { servicePortCfgInfoEntry 9 }

		
		-- 1.3.6.1.4.1.34592.1.3.100.9.2.1.10
		servicePortCfgInfoEhterType OBJECT-TYPE
			SYNTAX NscrtvPonExtEtherType
			MAX-ACCESS read-create
			STATUS current
			DESCRIPTION
				"用户以太网帧类型
				pppoe 0x8863
				ipv6  0x86dd
				ipv4  0x0800"
			::= { servicePortCfgInfoEntry 10 }

		
		-- 1.3.6.1.4.1.34592.1.3.100.9.2.1.11
		servicePortCfgInfoUpTrafficProfileId OBJECT-TYPE
			SYNTAX Unsigned32 (0..256)
			MAX-ACCESS read-create
			STATUS current
			DESCRIPTION
				"上行流量模板号
				范围0~256，其中0表示流量模板无效"
			::= { servicePortCfgInfoEntry 11 }

		
		-- 1.3.6.1.4.1.34592.1.3.100.9.2.1.12
		servicePortCfgInfoDownTrafficProfileId OBJECT-TYPE
			SYNTAX Unsigned32 (0..256)
			MAX-ACCESS read-create
			STATUS current
			DESCRIPTION
				"下行流量模板号
				范围0~256，其中0表示流量模板无效"
			::= { servicePortCfgInfoEntry 12 }

		
		-- 1.3.6.1.4.1.34592.1.3.100.9.2.1.13
		servicePortCfgInfoAdminStatus OBJECT-TYPE
			SYNTAX NscrtvPonExtAdminStatus
			MAX-ACCESS read-write
			STATUS current
			DESCRIPTION
				"管理状态，0表示失能，1表示使能"
			::= { servicePortCfgInfoEntry 13 }

		
		-- 1.3.6.1.4.1.34592.1.3.100.9.2.1.14
		servicePortCfgInfoOnuOnlineState OBJECT-TYPE
			SYNTAX NscrtvPonExtOnuOnlineState
			MAX-ACCESS read-only
			STATUS current
			DESCRIPTION
				"ONU在线状态，0表示不在线，1表示在线."
			::= { servicePortCfgInfoEntry 14 }

		
		-- 1.3.6.1.4.1.34592.1.3.100.9.2.1.15
		servicePortCfgInfoVlanTagAction OBJECT-TYPE
			SYNTAX NscrtvPonExtVlanTagAction
			MAX-ACCESS read-create
			STATUS current
			DESCRIPTION
				"VLAN TAG规则
				范围0~4
				0：default
				1：translate
				2：translate and add
				3：add double
				4：transparent
				5: vlan-transparent
				全透传可配置{5}，不关注SvlanId/UserVlanId
				若UserVlanId无效(单业务)可配置{0,3}
				若UserVlanId有效(多业务)可配置{0,1,2,4}"
			::= { servicePortCfgInfoEntry 15 }

		
		-- 1.3.6.1.4.1.34592.1.3.100.9.2.1.16
		servicePortCfgInfoVlanInnerVid OBJECT-TYPE
			SYNTAX Unsigned32 (1..4094)
			MAX-ACCESS read-create
			STATUS current
			DESCRIPTION
				"VLAN翻译内层VLAN号
				范围1~4094
				仅当VLAN TAG规则为{2,3}有效."
			::= { servicePortCfgInfoEntry 16 }

		
		-- 1.3.6.1.4.1.34592.1.3.100.9.2.1.17
		servicePortCfgInfoVlanInnerPri OBJECT-TYPE
			SYNTAX Unsigned32 (0..7)
			MAX-ACCESS read-create
			STATUS current
			DESCRIPTION
				"VLAN翻译内层VLAN优先级
				范围0~7
				仅当VLAN TAG规则为{2,3}有效"
			::= { servicePortCfgInfoEntry 17 }

		
		-- 1.3.6.1.4.1.34592.1.3.100.9.2.1.18
		servicePortCfgInfoDescription OBJECT-TYPE
			SYNTAX OCTET STRING (SIZE (0..64))
			MAX-ACCESS read-write
			STATUS current
			DESCRIPTION
				"描述信息"
			::= { servicePortCfgInfoEntry 18 }

		
		-- 1.3.6.1.4.1.34592.1.3.100.9.2.1.19
		servicePortCfgInfoPerfStat OBJECT-TYPE
			SYNTAX NscrtvPonExtPerfStat
			MAX-ACCESS read-write
			STATUS current
			DESCRIPTION
				"统计开关状态
				范围0~1， 其中0表示关闭统计，1表示开启统计"
			::= { servicePortCfgInfoEntry 19 }

		
		-- 1.3.6.1.4.1.34592.1.3.100.9.2.1.20
		servicePortCfgInfoRowStatus OBJECT-TYPE
			SYNTAX RowStatus
			MAX-ACCESS read-create
			STATUS current
			DESCRIPTION
				"行状态"
			::= { servicePortCfgInfoEntry 20 }

		
		-- 1.3.6.1.4.1.34592.1.3.100.9.3
		servicePortAutoCfgInfoTable OBJECT-TYPE
			SYNTAX SEQUENCE OF ServicePortAutoCfgInfoEntry
			MAX-ACCESS not-accessible
			STATUS current
			DESCRIPTION
				"业务虚端口自动配置信息表"
			::= { servicePortObjects 3 }

		
		-- 1.3.6.1.4.1.34592.1.3.100.9.3.1
		servicePortAutoCfgInfoEntry OBJECT-TYPE
			SYNTAX ServicePortAutoCfgInfoEntry
			MAX-ACCESS not-accessible
			STATUS current
			DESCRIPTION
				"Description."
			INDEX { servicePortAutoCfgInfoDeviceIndex, servicePortAutoCfgInfoCardIndex, servicePortAutoCfgInfoPonPortIndex }
			::= { servicePortAutoCfgInfoTable 1 }

		
		ServicePortAutoCfgInfoEntry ::=
			SEQUENCE { 
				servicePortAutoCfgInfoDeviceIndex
					NscrtvPonExtDeviceIndex,
				servicePortAutoCfgInfoCardIndex
					NscrtvPonExtCardIndex,
				servicePortAutoCfgInfoPonPortIndex
					Unsigned32,
				servicePortAutoCfgInfoSvlanId
					Unsigned32,
				servicePortAutoCfgInfoGemId
					Unsigned32,
				servicePortAutoCfgInfoUserVlanId
					Unsigned32,
				servicePortAutoCfgInfoVlanTagAction
					NscrtvPonExtVlanTagAction,
				servicePortAutoCfgInfoVlanInnerVid
					Unsigned32,
				servicePortAutoCfgInfoVlanInnerPri
					Unsigned32,
				servicePortAutoCfgInfoUpTrafficProfileId
					Unsigned32,
				servicePortAutoCfgInfoDownTrafficProfileId
					Unsigned32,
				servicePortAutoCfgInfoMode
					NscrtvPonExtAutoMode
			 }

		-- 1.3.6.1.4.1.34592.1.3.100.9.3.1.1
		servicePortAutoCfgInfoDeviceIndex OBJECT-TYPE
			SYNTAX NscrtvPonExtDeviceIndex
			MAX-ACCESS not-accessible
			STATUS current
			DESCRIPTION
				"OLT设备索引号        
				一个OLT节点可以由多台OLT设备组成。节点内的每台OLT设备由OLT设备索引号唯一标识"
			::= { servicePortAutoCfgInfoEntry 1 }

		
		-- 1.3.6.1.4.1.34592.1.3.100.9.3.1.2
		servicePortAutoCfgInfoCardIndex OBJECT-TYPE
			SYNTAX NscrtvPonExtCardIndex
			MAX-ACCESS not-accessible
			STATUS current
			DESCRIPTION
				"板卡索引号"
			::= { servicePortAutoCfgInfoEntry 2 }

		
		-- 1.3.6.1.4.1.34592.1.3.100.9.3.1.3
		servicePortAutoCfgInfoPonPortIndex OBJECT-TYPE
			SYNTAX Unsigned32
			MAX-ACCESS not-accessible
			STATUS current
			DESCRIPTION
				"PON端口索引号，范围1~8"
			::= { servicePortAutoCfgInfoEntry 3 }

		
		-- 1.3.6.1.4.1.34592.1.3.100.9.3.1.4
		servicePortAutoCfgInfoSvlanId OBJECT-TYPE
			SYNTAX Unsigned32 (1..4094)
			MAX-ACCESS read-write
			STATUS current
			DESCRIPTION
				"上联口VLAN号
				范围1~4094"
			::= { servicePortAutoCfgInfoEntry 4 }

		
		-- 1.3.6.1.4.1.34592.1.3.100.9.3.1.5
		servicePortAutoCfgInfoGemId OBJECT-TYPE
			SYNTAX Unsigned32 (1..30)
			MAX-ACCESS read-write
			STATUS current
			DESCRIPTION
				"GEM号
				范围1~30"
			::= { servicePortAutoCfgInfoEntry 5 }

		
		-- 1.3.6.1.4.1.34592.1.3.100.9.3.1.6
		servicePortAutoCfgInfoUserVlanId OBJECT-TYPE
			SYNTAX Unsigned32 (0..4094)
			MAX-ACCESS read-write
			STATUS current
			DESCRIPTION
				"用户VLAN号
				范围0~4094，若为0表示用户VLAN无效"
			::= { servicePortAutoCfgInfoEntry 6 }

		
		-- 1.3.6.1.4.1.34592.1.3.100.9.3.1.7
		servicePortAutoCfgInfoVlanTagAction OBJECT-TYPE
			SYNTAX NscrtvPonExtVlanTagAction
			MAX-ACCESS read-write
			STATUS current
			DESCRIPTION
				"VLAN TAG规则
				范围0~4
				0：default
				1：translate
				2：translate and add
				3：add double
				4：transparent
				若用户VLAN无效可配置{0，3}
				若用户VLAN有效可可配置{0,1,2,4}"
			::= { servicePortAutoCfgInfoEntry 7 }

		
		-- 1.3.6.1.4.1.34592.1.3.100.9.3.1.8
		servicePortAutoCfgInfoVlanInnerVid OBJECT-TYPE
			SYNTAX Unsigned32 (1..4094)
			MAX-ACCESS read-write
			STATUS current
			DESCRIPTION
				"VLAN翻译内层VLAN号
				范围1~4094
				仅当VLAN TAG规则为{2,3}有效"
			::= { servicePortAutoCfgInfoEntry 8 }

		
		-- 1.3.6.1.4.1.34592.1.3.100.9.3.1.9
		servicePortAutoCfgInfoVlanInnerPri OBJECT-TYPE
			SYNTAX Unsigned32 (0..7)
			MAX-ACCESS read-write
			STATUS current
			DESCRIPTION
				"VLAN翻译内层VLAN优先级
				范围0~7
				仅当VLAN TAG规则为{2,3}有效"
			::= { servicePortAutoCfgInfoEntry 9 }

		
		-- 1.3.6.1.4.1.34592.1.3.100.9.3.1.10
		servicePortAutoCfgInfoUpTrafficProfileId OBJECT-TYPE
			SYNTAX Unsigned32 (0..256)
			MAX-ACCESS read-write
			STATUS current
			DESCRIPTION
				"上行流量模板号
				范围0~256，其中0表示流量模板无效"
			::= { servicePortAutoCfgInfoEntry 10 }

		
		-- 1.3.6.1.4.1.34592.1.3.100.9.3.1.11
		servicePortAutoCfgInfoDownTrafficProfileId OBJECT-TYPE
			SYNTAX Unsigned32 (0..256)
			MAX-ACCESS read-write
			STATUS current
			DESCRIPTION
				"下行流量模板号
				范围0~256，其中0表示流量模板无效"
			::= { servicePortAutoCfgInfoEntry 11 }

		
		-- 1.3.6.1.4.1.34592.1.3.100.9.3.1.12
		servicePortAutoCfgInfoMode OBJECT-TYPE
			SYNTAX NscrtvPonExtAutoMode
			MAX-ACCESS read-write
			STATUS current
			DESCRIPTION
				"自动配置模式
				范围0~1,0表示自动模式，1表示手动模式"
			::= { servicePortAutoCfgInfoEntry 12 }

		
		-- 1.3.6.1.4.1.34592.1.3.100.9.4
		servicePortCurPerfStatTable OBJECT-TYPE
			SYNTAX SEQUENCE OF ServicePortCurPerfStatEntry
			MAX-ACCESS not-accessible
			STATUS current
			DESCRIPTION
				"业务虚端口当前性能统计表"
			::= { servicePortObjects 4 }

		
		-- 1.3.6.1.4.1.34592.1.3.100.9.4.1
		servicePortCurPerfStatEntry OBJECT-TYPE
			SYNTAX ServicePortCurPerfStatEntry
			MAX-ACCESS not-accessible
			STATUS current
			DESCRIPTION
				"Description."
			INDEX { servicePortCurPerfStatDeviceIndex, servicePortCurPerfStatCardIndex, servicePortCurPerfStatIndex }
			::= { servicePortCurPerfStatTable 1 }

		
		ServicePortCurPerfStatEntry ::=
			SEQUENCE { 
				servicePortCurPerfStatDeviceIndex
					NscrtvPonExtDeviceIndex,
				servicePortCurPerfStatCardIndex
					NscrtvPonExtCardIndex,
				servicePortCurPerfStatIndex
					Unsigned32,
				servicePortCurPerfStatOutOctets
					Counter64,
				servicePortCurPerfStatOutPkts
					Counter64,
				servicePortCurPerfStatInOctets
					Counter64,
				servicePortCurPerfStatInPkts
					Counter64,
				servicePortCurPerfStatClear
					NscrtvPonExtCurPerfStatClear
			 }

		-- 1.3.6.1.4.1.34592.1.3.100.9.4.1.1
		servicePortCurPerfStatDeviceIndex OBJECT-TYPE
			SYNTAX NscrtvPonExtDeviceIndex
			MAX-ACCESS not-accessible
			STATUS current
			DESCRIPTION
				"OLT设备索引号        
				一个OLT节点可以由多台OLT设备组成。节点内的每台OLT设备由OLT设备索引号唯一标识"
			::= { servicePortCurPerfStatEntry 1 }

		
		-- 1.3.6.1.4.1.34592.1.3.100.9.4.1.2
		servicePortCurPerfStatCardIndex OBJECT-TYPE
			SYNTAX NscrtvPonExtCardIndex
			MAX-ACCESS not-accessible
			STATUS current
			DESCRIPTION
				"板卡索引号"
			::= { servicePortCurPerfStatEntry 2 }

		
		-- 1.3.6.1.4.1.34592.1.3.100.9.4.1.3
		servicePortCurPerfStatIndex OBJECT-TYPE
			SYNTAX Unsigned32
			MAX-ACCESS not-accessible
			STATUS current
			DESCRIPTION
				"业务虚端口索引号"
			::= { servicePortCurPerfStatEntry 3 }

		
		-- 1.3.6.1.4.1.34592.1.3.100.9.4.1.4
		servicePortCurPerfStatOutOctets OBJECT-TYPE
			SYNTAX Counter64
			UNITS "bytes"
			MAX-ACCESS read-only
			STATUS current
			DESCRIPTION
				"上行报文字节数"
			::= { servicePortCurPerfStatEntry 4 }

		
		-- 1.3.6.1.4.1.34592.1.3.100.9.4.1.5
		servicePortCurPerfStatOutPkts OBJECT-TYPE
			SYNTAX Counter64
			MAX-ACCESS read-only
			STATUS current
			DESCRIPTION
				"上行报文包数"
			::= { servicePortCurPerfStatEntry 5 }

		
		-- 1.3.6.1.4.1.34592.1.3.100.9.4.1.6
		servicePortCurPerfStatInOctets OBJECT-TYPE
			SYNTAX Counter64
			UNITS "bytes"
			MAX-ACCESS read-only
			STATUS current
			DESCRIPTION
				"下行报文字节数，仅当业务虚端口开启下行限速后该项有效"
			::= { servicePortCurPerfStatEntry 6 }

		
		-- 1.3.6.1.4.1.34592.1.3.100.9.4.1.7
		servicePortCurPerfStatInPkts OBJECT-TYPE
			SYNTAX Counter64
			MAX-ACCESS read-only
			STATUS current
			DESCRIPTION
				"下行报文包数，仅当业务虚端口开启下行限速后该项有效"
			::= { servicePortCurPerfStatEntry 7 }

		
		-- 1.3.6.1.4.1.34592.1.3.100.9.4.1.8
		servicePortCurPerfStatClear OBJECT-TYPE
			SYNTAX NscrtvPonExtCurPerfStatClear
			MAX-ACCESS read-write
			STATUS current
			DESCRIPTION
				"报文清除，0为不清除，1为清除报文统计"
			::= { servicePortCurPerfStatEntry 8 }

		
		-- 1.3.6.1.4.1.34592.1.3.100.9.5
		servicePortCollectTable OBJECT-TYPE
			SYNTAX SEQUENCE OF ServicePortCollectEntry
			MAX-ACCESS not-accessible
			STATUS current
			DESCRIPTION
				"Description."
			::= { servicePortObjects 5 }

		
		-- 1.3.6.1.4.1.34592.1.3.100.9.5.1
		servicePortCollectEntry OBJECT-TYPE
			SYNTAX ServicePortCollectEntry
			MAX-ACCESS not-accessible
			STATUS current
			DESCRIPTION
				"Description."
			INDEX { servicePortCollectIndex }
			::= { servicePortCollectTable 1 }

		
		ServicePortCollectEntry ::=
			SEQUENCE { 
				servicePortCollectIndex
					Integer32,
				servicePortCollectInformation
					OCTET STRING
			 }

		-- 1.3.6.1.4.1.34592.1.3.100.9.5.1.1
		servicePortCollectIndex OBJECT-TYPE
			SYNTAX Integer32
			MAX-ACCESS not-accessible
			STATUS current
			DESCRIPTION
				"Description."
			::= { servicePortCollectEntry 1 }

		
		-- 1.3.6.1.4.1.34592.1.3.100.9.5.1.2
		servicePortCollectInformation OBJECT-TYPE
			SYNTAX OCTET STRING
			MAX-ACCESS read-only
			STATUS current
			DESCRIPTION
				"Description."
			::= { servicePortCollectEntry 2 }

		
	
	END

--
-- NSCRTV-PON-TREE-EXT-SERVICE-PORT-MIB.my
--
