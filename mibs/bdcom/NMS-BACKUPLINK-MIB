NMS-BACKUPLINK-MIB DEFINITIONS ::= BEGIN    

	IMPORTS
		MODULE-IDENTITY, OBJECT-TYPE, Counter32, TimeTicks
			FROM SNMPv2-SMI
		DisplayString, MacAddress, TEXTUAL-CONVENTION, TruthValue, RowStatus
			FROM SNMPv2-TC
		MODULE-COMPLIANCE, OBJECT-GROUP
			FROM SNMPv2-CONF
		InterfaceIndex
			FROM IF-MIB
		PortList
			FROM Q-BRIDGE-MIB
		nmsMgmt
			FROM NMS-SMI;
    
    backupLinkState ::= TEXTUAL-CONVENTION
    STATUS  current  
    DESCRIPTION
        "The  backupLink port state."
    SYNTAX  INTEGER { 
    	up(0),
        down(1), 
        nosetting(2)
    }

    PreemptionMode ::= TEXTUAL-CONVENTION
    STATUS  current  
    DESCRIPTION
        "The preemption mode of backupLink group."
    SYNTAX  INTEGER {
    	forced(0),
        bandwidth(1),
        nopreemption(2)
    }
      
    MMU ::= TEXTUAL-CONVENTION
    STATUS  current  
    DESCRIPTION
        "MAC-adress move update."
    SYNTAX  INTEGER {
    	transmit(0),
        receive(1),
        no_mmu(2)
    }     
    
    MonitorLinkState ::= TEXTUAL-CONVENTION
    STATUS  current  
    DESCRIPTION
        "The  monitorLink port state."
    SYNTAX  INTEGER { 
    	up(0),
        down(1), 
        nosetting(2)
    }
                
    nmsBackupLinkMIB MODULE-IDENTITY
        LAST-UPDATED "201104290000Z"
        ORGANIZATION ""
        CONTACT-INFO ""    
        DESCRIPTION  "MIB module for backuplink"
        ::= { nmsMgmt 254 }    
  
    nmsBackupLinkGroupTable OBJECT-TYPE
        SYNTAX      SEQUENCE OF NmsBackupLinkGroupEntry
        MAX-ACCESS  not-accessible
        STATUS      current
        ::= { nmsBackupLinkMIB 1 }
            
    nmsBackupLinkGroupEntry OBJECT-TYPE
        SYNTAX      NmsBackupLinkGroupEntry
        MAX-ACCESS  not-accessible
        STATUS      current  
        INDEX { nmsBLGID } 
        ::= { nmsBackupLinkGroupTable 1 } 

    NmsBackupLinkGroupEntry ::=
    SEQUENCE {
        nmsBLGID
            InterfaceIndex,
        nmsBLGActivePortID
            InterfaceIndex, 
        nmsBLGActivePortState
            backupLinkState,       
        nmsBLGActiveFdbUpdate
            MMU,
        nmsBLGBackupPortID
            InterfaceIndex, 
        nmsBLGBackupPortState
            backupLinkState,      
        nmsBLGBackupShareLoadVlan
            OCTET STRING,      
        nmsBLGBackupVlanState
            backupLinkState,      
        nmsBLGBackupFdbUpdate
            MMU,
        nmsBLGPreemptionMode
            PreemptionMode,
        nmsBLGPreemptionDelay
            INTEGER,
        nmsBLGSwitchCount
            INTEGER,
        nmsBLGFdbUpdateTxCount
            INTEGER, 
        nmsBLGRowStatus
        	RowStatus
    }
      
    nmsBLGID OBJECT-TYPE
        SYNTAX       InterfaceIndex
   		MAX-ACCESS   not-accessible
    	STATUS       current
        DESCRIPTION
            "The BackupLink group id."
    ::= { nmsBackupLinkGroupEntry 1 }
    
    nmsBLGActivePortID  OBJECT-TYPE
        SYNTAX       InterfaceIndex
   		MAX-ACCESS   read-write
    	STATUS       current
        DESCRIPTION
            "The port id of the BackupLink group active port."
    ::= { nmsBackupLinkGroupEntry 2 } 
   
    nmsBLGActivePortState OBJECT-TYPE
        SYNTAX       backupLinkState
   		MAX-ACCESS   read-only
    	STATUS       current
        DESCRIPTION
            "The port state of the BackupLink group active port."
    ::= { nmsBackupLinkGroupEntry 3 }
    
    nmsBLGActiveFdbUpdate OBJECT-TYPE
        SYNTAX       MMU
   		MAX-ACCESS   read-write
    	STATUS       current
        DESCRIPTION
            "The port mmuType of the BackupLink group active port."
    ::= { nmsBackupLinkGroupEntry 4 }
    
    nmsBLGBackupPortID  OBJECT-TYPE
        SYNTAX       InterfaceIndex
   		MAX-ACCESS   read-write
    	STATUS       current
        DESCRIPTION
            "The port id of the BackupLink group backup port."
    ::= { nmsBackupLinkGroupEntry 5 }   
           
    nmsBLGBackupPortState OBJECT-TYPE
        SYNTAX       backupLinkState
   		MAX-ACCESS   read-only
    	STATUS       current
        DESCRIPTION
            "The port state of the BackupLink group backup port."
    ::= { nmsBackupLinkGroupEntry 6 }
     
    nmsBLGBackupFdbUpdate OBJECT-TYPE
        SYNTAX       MMU
   		MAX-ACCESS   read-write
    	STATUS       current
        DESCRIPTION
            "The port mmuType of the BackupLink group backup port."
    ::= { nmsBackupLinkGroupEntry 7 }
    
    nmsBLGBackupShareLoadVlan OBJECT-TYPE
        SYNTAX       OCTET STRING
   		MAX-ACCESS   read-write
    	STATUS       current
        DESCRIPTION
            "The share load vlan  of the BackupLink group."
    ::= { nmsBackupLinkGroupEntry 8 } 
                                                                       
    nmsBLGBackupVlanState OBJECT-TYPE
        SYNTAX       backupLinkState
   		MAX-ACCESS   read-only
    	STATUS       current
        DESCRIPTION
            "The backup port state of the BackupLink group in the backup vlan."
    ::= { nmsBackupLinkGroupEntry 9 }
    
    nmsBLGPreemptionMode  OBJECT-TYPE
        SYNTAX       PreemptionMode
   		MAX-ACCESS   read-write
    	STATUS       current
        DESCRIPTION
            "The preemption mode of the BackupLink group."
    ::= { nmsBackupLinkGroupEntry 10 } 
    
    nmsBLGPreemptionDelay    OBJECT-TYPE
        SYNTAX       INTEGER
   		MAX-ACCESS   read-write
    	STATUS       current
        DESCRIPTION
            "The preemption delay timer of the BackupLink group."
    ::= { nmsBackupLinkGroupEntry 11 }  
    
    nmsBLGSwitchCount OBJECT-TYPE
        SYNTAX       INTEGER
   		MAX-ACCESS   read-only
    	STATUS       current
        DESCRIPTION
            "The switch counts of the BackupLink group."
    ::= { nmsBackupLinkGroupEntry 12 }  
    
    nmsBLGFdbUpdateTxCount OBJECT-TYPE
        SYNTAX       INTEGER
   		MAX-ACCESS   read-only
    	STATUS       current
        DESCRIPTION
            "The Tx counts of the BackupLink group."
    ::= { nmsBackupLinkGroupEntry 13 }
    
    nmsBLGRowStatus OBJECT-TYPE
        SYNTAX       RowStatus
        MAX-ACCESS   read-create
        STATUS       current
        DESCRIPTION
            "Create a new BackupLink group."
    ::= { nmsBackupLinkGroupEntry 14 }   
    
    nmsMonitorLinkUplinkGroupTable OBJECT-TYPE
        SYNTAX      SEQUENCE OF NMSMonitorLinkUplinkGroupEntry
        MAX-ACCESS  not-accessible
        STATUS      current
        ::= { nmsBackupLinkMIB 2 }
        
    nmsMonitorLinkUplinkGroupEntry OBJECT-TYPE
        SYNTAX      NMSMonitorLinkUplinkGroupEntry
        MAX-ACCESS  not-accessible
        STATUS      current  
        INDEX { nmsMLGUplinkPortID } 
        ::= { nmsMonitorLinkUplinkGroupTable 1 } 
        
    NMSMonitorLinkUplinkGroupEntry ::=
    SEQUENCE {  
        nmsMLGID
            InterfaceIndex,
        nmsMLGUplinkPortID
            InterfaceIndex,
        nmsMLGUplinkPortState
            MonitorLinkState,       
        nmsMLGUplinkRowStatus
        	RowStatus
    }
    
    nmsMLGID OBJECT-TYPE
        SYNTAX       InterfaceIndex
   		MAX-ACCESS   not-accessible
    	STATUS       current
        DESCRIPTION
            "The MonitorLink group id."
    ::= { nmsMonitorLinkUplinkGroupEntry 1 }
    
    nmsMLGUplinkPortID  OBJECT-TYPE
        SYNTAX       InterfaceIndex
   		MAX-ACCESS   read-write
    	STATUS       current
        DESCRIPTION
            "The port id of the MonitorLink group uplink port."
    ::= { nmsMonitorLinkUplinkGroupEntry 2 }
    
    nmsMLGUplinkPortState OBJECT-TYPE
        SYNTAX       MonitorLinkState
   		MAX-ACCESS   read-only
    	STATUS       current
        DESCRIPTION
            "The port state of the MonitorLink group uplink port."
    ::= { nmsMonitorLinkUplinkGroupEntry 3 }
    
    nmsMLGUplinkRowStatus OBJECT-TYPE
        SYNTAX       RowStatus
        MAX-ACCESS   read-create
        STATUS       current
        DESCRIPTION
            "The port linkstate of the MonitorLink group uplink port."
        ::= { nmsMonitorLinkUplinkGroupEntry 4 } 
        
    nmsMonitorLinkDownlinkGroupTable OBJECT-TYPE
        SYNTAX      SEQUENCE OF NmsMonitorLinkDownlinkGroupEntry
        MAX-ACCESS  not-accessible
        STATUS      current
        ::= { nmsBackupLinkMIB 3 }   
        
    nmsMonitorLinkDownlinkGroupEntry OBJECT-TYPE
        SYNTAX      NmsMonitorLinkDownlinkGroupEntry
        MAX-ACCESS  not-accessible
        STATUS      current  
        INDEX { nmsMLGID, nmsMLGDownlinkIndex } 
        ::= { nmsMonitorLinkDownlinkGroupTable 1 }     
    
    NmsMonitorLinkDownlinkGroupEntry ::=
    SEQUENCE {  
        nmsMLGID
            InterfaceIndex,
        nmsMLGDownlinkIndex 
            InterfaceIndex,     
        nmsMLGDownlinkPortState  
            MonitorLinkState,
        nmsMLGDownlinkRowStatus
        	RowStatus
    }    
    
    nmsMLGID OBJECT-TYPE
        SYNTAX       InterfaceIndex
   		MAX-ACCESS   not-accessible
    	STATUS       current
        DESCRIPTION
            "The MonitorLink group id."
    ::= { nmsMonitorLinkDownlinkGroupEntry 1 } 
    
    nmsMLGDownlinkIndex OBJECT-TYPE
        SYNTAX       InterfaceIndex
   		MAX-ACCESS   read-only
    	STATUS       current
        DESCRIPTION
            "The port id of the MonitorLink group downlink port."
    ::= { nmsMonitorLinkDownlinkGroupEntry 2 }
    
    nmsMLGDownlinkPortState OBJECT-TYPE
        SYNTAX       MonitorLinkState
   		MAX-ACCESS   read-only
    	STATUS       current
        DESCRIPTION
            "The port state of the MonitorLink group downlink port."
    ::= { nmsMonitorLinkDownlinkGroupEntry 3 }
        
    nmsMLGDownlinkRowStatus OBJECT-TYPE
        SYNTAX       RowStatus
        MAX-ACCESS   read-create
        STATUS       current
        DESCRIPTION
            "The port linkstate of the MonitorLink group downlink port."
    ::= { nmsMonitorLinkDownlinkGroupEntry 4 }
    END
