-- Bridgetech MIB types
-- All Bridgetech devices with SNMP support

BtechTypes-MIB DEFINITIONS ::= BEGIN

Uint8  ::= INTEGER (0..255)
--         "An unsigned 8 bits integer (byte)"

Uint16 ::= INTEGER (0..65535)
--         "An unsigned 16 bits integer"

Uint32 ::= INTEGER (0.. 4294967295)
--         "An unsigned 32 bits integer"

PIDNumber    ::= INTEGER (0..8191)
--         "The number of a PID."

UdpPort      ::= INTEGER(0..65535)
--         "Multicast/TCP/UDP port."

RowStatus ::= INTEGER {
               active(1),
               notInService(2),
               notReady(3),
               createAndGo(4),  -- supported for setting
               createAndWait(5),
               destroy(6)       -- supported for setting
               }
--         "The RowStatus as defined in SNMPv2-TC (RFC1903). Used for creating
--         and deleting conceptual rows. For more information, please refer to
--         RFC1903."

END
