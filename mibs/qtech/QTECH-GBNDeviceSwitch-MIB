QTECH-GBNDeviceSwitch-MIB DEFINITIONS ::= BEGIN

    IMPORTS
        MODULE-IDENTITY, OBJECT-TYPE,
        Integer32, IpAddress, 
        NOTIFICATION-TYPE                       FROM SNMPv2-SMI
        
        DisplayString, MacAddress,
        RowStatus, TruthValue,DateAndTime       FROM SNMPv2-TC
        
        MODULE-COMPLIANCE, OBJECT-GROUP         FROM SNMPv2-CONF
        
        gbnDevice                               FROM QTECH-MASTER-MIB
        
        SnmpAdminString                         FROM SNMP-FRAMEWORK-MIB
        
        VlanIndex                               FROM Q-BRIDGE-MIB
        
        PortList, dot1qStaticMulticastEntry     FROM Q-BRIDGE-MIB;       

    gbnDeviceSwitch MODULE-IDENTITY
        LAST-UPDATED    "0011020000Z"  -- November 2, 2000
        ORGANIZATION    "QTECH LLC"
        CONTACT-INFO    "Basil Budko
                         E-mail: budko@qtech.ru"

        DESCRIPTION     "Gbn Common Enterprise MIB definition."

        REVISION        "0011020000Z"  -- November 2, 2000
        DESCRIPTION     "Initial MIB creation."

        ::= { gbnDevice 1 }

MirrorMacType ::= TEXTUAL-CONVENTION
    STATUS      current
    DESCRIPTION
       "null、destination、source"
    SYNTAX      INTEGER { null(0), destination (1), source(2) }  
    
------------------------------------------------------------------------------
--  define groups in gbnDeviceSwitch-MIB
------------------------------------------------------------------------------
    gbnDeviceSwitchMirror          OBJECT IDENTIFIER ::= { gbnDeviceSwitch 1 }
    gbnDeviceSwitchPort            OBJECT IDENTIFIER ::= { gbnDeviceSwitch 2 }
    gbnDeviceSwitchAggregation     OBJECT IDENTIFIER ::= { gbnDeviceSwitch 3 }
    gbnDeviceSwitchL3              OBJECT IDENTIFIER ::= { gbnDeviceSwitch 4 }
    gbnDeviceSwitchLoopTest        OBJECT IDENTIFIER ::= { gbnDeviceSwitch 5 }
    gbnDeviceSwitchSRM             OBJECT IDENTIFIER ::= { gbnDeviceSwitch 6 }
    gbnDeviceSwitchFlowAlarm     OBJECT IDENTIFIER ::= { gbnDeviceSwitch 7 }    
    gbnDeviceSwitchQueneScheduer    OBJECT IDENTIFIER ::= { gbnDeviceSwitch 8 }
    gbnDeviceSwitchLineRate       OBJECT IDENTIFIER ::= { gbnDeviceSwitch 9 }
    gbnDeviceSwitchPortIsolation         OBJECT IDENTIFIER ::= { gbnDeviceSwitch 10 }
    gbnDeviceSwitchStormControl        OBJECT IDENTIFIER ::= { gbnDeviceSwitch 11 }
    gbnDeviceSwitchAntiDos        OBJECT IDENTIFIER ::= { gbnDeviceSwitch 12 }
    gbnDeviceSwitchBandWidth        OBJECT IDENTIFIER ::= { gbnDeviceSwitch 13 }
    
------------------------------------------------------------------------------
--
--  gbnDeviceSwitchMirror - Mirror Group                    
--
------------------------------------------------------------------------------
    mirroringPort OBJECT-TYPE
        SYNTAX INTEGER (0..26)
        MAX-ACCESS read-write
        STATUS current
        DESCRIPTION
            "This port which all packets send to." 
        ::= { gbnDeviceSwitchMirror 1 }

    mirroredEgrPort OBJECT-TYPE
        SYNTAX      PortList
        MAX-ACCESS  read-write
        STATUS      current
        DESCRIPTION
             "The egress ports which need to monitor."
        ::= { gbnDeviceSwitchMirror 2 }
        
    mirroredIgrPort OBJECT-TYPE
        SYNTAX      PortList
        MAX-ACCESS  read-write
        STATUS      current
        DESCRIPTION
            "The ingress ports which need to monitor."
            ::= { gbnDeviceSwitchMirror 3 }

    ingressMirrorMac OBJECT-TYPE
        SYNTAX      MacAddress
        MAX-ACCESS  read-write
        STATUS      current
        DESCRIPTION
            "The MAC address which will be compared with the ingress frame, Only the matched frame will be mirrored"
            --用于匹配ingress报文的MAC地址
        ::= { gbnDeviceSwitchMirror 4 }

    egressMirrorMac OBJECT-TYPE
        SYNTAX      MacAddress
        MAX-ACCESS  read-write
        STATUS      current
        DESCRIPTION
            "The MAC address which will be compared with the egress frame, Only the matched frame will be mirrored"
            --用于匹配egress报文的MAC地址
        ::= { gbnDeviceSwitchMirror 5 }

    ingressMirrorMacType OBJECT-TYPE
        SYNTAX      MirrorMacType
        MAX-ACCESS  read-write
        STATUS      current
        DESCRIPTION
            "The destination or source MAC address which will be compared with the ingress frame"
            --指定用于匹配ingress报文的是目的还是源MAC地址
        ::= { gbnDeviceSwitchMirror 6 }    

    egressMirrorMacType OBJECT-TYPE
        SYNTAX      MirrorMacType
        MAX-ACCESS  read-write
        STATUS      current
        DESCRIPTION
            "The destination or source MAC address which will be compared with the egress frame"
            --指定用于匹配egress报文的是目的还是源MAC地址
        ::= { gbnDeviceSwitchMirror 7 }     

    ingressMirrorDivider OBJECT-TYPE
        SYNTAX      INTEGER(0..1023)
        MAX-ACCESS  read-write
        STATUS      current
        DESCRIPTION
            "the mirror sampling divider"
            --ingress报文的采样值
        ::= { gbnDeviceSwitchMirror 8 }        

    egressMirrorDivider OBJECT-TYPE
        SYNTAX      INTEGER(0..1023)
        MAX-ACCESS  read-write
        STATUS      current
        DESCRIPTION
            "the mirror sampling divider"
            --egress报文的采样值
        ::= { gbnDeviceSwitchMirror 9 }          
    
------------------------------------------------------------------------------
--
--  gbnDeviceSwitchPort - Port Group                    
--
------------------------------------------------------------------------------
    portTypeTable OBJECT-TYPE
        SYNTAX SEQUENCE OF PortTypeEntry
        MAX-ACCESS not-accessible
        STATUS current
        DESCRIPTION
            "A table of switch interfaces and associated properties."
        ::= { gbnDeviceSwitchPort 1 }

    portTypeEntry OBJECT-TYPE
        SYNTAX PortTypeEntry
        MAX-ACCESS not-accessible
        STATUS current
        DESCRIPTION
            "Table entry for switch interface control and status information."
        INDEX { portNumber }
        ::= { portTypeTable 1 }

    PortTypeEntry ::= SEQUENCE {
        portNumber                INTEGER,
        portType                INTEGER

      }

    portNumber OBJECT-TYPE
        SYNTAX INTEGER (1..26)
        MAX-ACCESS read-only
        STATUS current
        DESCRIPTION
            "the index of port."
        ::= { portTypeEntry 1 }

    portType OBJECT-TYPE
        SYNTAX INTEGER {
             blank(1),
             fE(2),
             single100FX(3),
             double100FX(4),
             single1000FX(5),
             double1000FX(6),
             fE1000(7),
             cpu(8)
        }
        MAX-ACCESS read-only
        STATUS current
        DESCRIPTION
            "端口类型:1为不存在；2为10/100M电口；3为100M单模光纤；
            4为100M多模光纤；5为1000M单模光纤；6为1000M多模光纤；
            7为1000M电口; 8为CPU接口"
        ::= { portTypeEntry 2 }

------------------------------------------------------------------------------
--
--  gbnDeviceSwitchAggregation - Port Trunk Group                    
--
------------------------------------------------------------------------------
    aggTable OBJECT-TYPE
        SYNTAX      SEQUENCE OF AggEntry
        MAX-ACCESS  not-accessible
        STATUS      obsolete
        DESCRIPTION
            "A table that contains information about every
            Aggregator that is associated with this System."
        ::= { gbnDeviceSwitchAggregation 1 }
    
    aggEntry OBJECT-TYPE
        SYNTAX      AggEntry
        MAX-ACCESS  not-accessible
        STATUS      obsolete
        DESCRIPTION
            "A list of the Aggregator parameters. This is indexed
            by the ifIndex of the Aggregator."
        INDEX { aggUnit, aggPort }
        ::= { aggTable 1 }
    
       AggEntry ::=
        SEQUENCE {
            aggUnit
               INTEGER,
            aggPort
               INTEGER,
            aggPortListPorts
               PortList,
            aggRule
               INTEGER,
            aggRowstatus
               RowStatus
        }

    aggUnit OBJECT-TYPE
        SYNTAX       INTEGER
        MAX-ACCESS   read-only
        STATUS       obsolete
        DESCRIPTION
            "The Interface Unit of the Aggregation."
        ::= { aggEntry 1 }
    
    aggPort OBJECT-TYPE
        SYNTAX       INTEGER
        MAX-ACCESS   read-only
        STATUS       obsolete
        DESCRIPTION
            "The MasterPort of the Aggregation."
        ::= { aggEntry 2 }
           
    aggPortListPorts OBJECT-TYPE
        SYNTAX      PortList
        MAX-ACCESS  read-write
        STATUS      obsolete
        DESCRIPTION
            "The complete set of ports currently associated with
             this Aggregator.  Each bit set in this list represents
             an Actor Port member of this Link Aggregation."
        ::= { aggEntry 3 }

    aggRule OBJECT-TYPE
	SYNTAX INTEGER {
		srcMAC(1),
		destMAC(2),
		srcXORDestMAC(3),
		srcIP(4),
		destIP(5),
		srcXORDestIP(6)
	}
	ACCESS read-write
	STATUS obsolete
	DESCRIPTION
		" The Rule to be applied to this Link Aggregator's Trunk Group
		Table. The rules are based on the following selections SrcMAC (1),
		means that the last three bits of the Source MAC Address are used to
		index the Trunk Group to get the destination port. DestMAC (2), means
		the last three bits of the Destination MAC Address are used to index 
		into the Trunk Group to get the destination port. SrcXORDestMAC (3),
		means that the last three bits of the Source MAC Address are logically
		XORed with the last three bits of the Destination MAC Address and used
		to index into the Trunk Group to get the destination port. SrcIP (4),
		means the last three bits of the Source IP Address are used to index
		into the Trunk Group to get the destination port. DestIP (5), means
		the last three bits of the Destination IP Address are used to index
		into the Trunk Group to get the destination port. SrcXORDestIP (6),
		means the last three bits of the Source IP Address are logically XORed
		with the last three bits of the Destination IP Address and used to 
		index into the Trunk Group to get the destination port. This rule
		defines the distribution algorithm applied to the aggregated link."
	::= { aggEntry 4 }

    aggRowstatus OBJECT-TYPE
        SYNTAX       TruthValue
        MAX-ACCESS   read-write
        STATUS       obsolete
        DESCRIPTION
            "rowstatus of trunk."
        ::= { aggEntry 5 }

------------------------------------------------------------------------------
--
--  gbnDeviceSwitchL3 - L3 Group                    
--
------------------------------------------------------------------------------
    l3Table OBJECT-TYPE 
	    SYNTAX      SEQUENCE OF L3Entry
	    MAX-ACCESS  not-accessible
	    STATUS      current
	    DESCRIPTION "此表为交换芯片的L3表项内容。" 
	    ::= { gbnDeviceSwitchL3 1 }     
	    
	l3Entry OBJECT-TYPE 
	    SYNTAX      L3Entry
	    MAX-ACCESS  not-accessible
	    STATUS      current
	    DESCRIPTION "交换芯片的L3表项，此表为只读。" 
	    INDEX   { l3IpAddress }
	    ::= { l3Table 1 } 
	    
    L3Entry ::= 
        SEQUENCE { 
            l3IpAddress          IpAddress, 
            l3NextHopMacAddress  MacAddress,
            l3Vlan               VlanIndex,
            l3Port               INTEGER,
            l3CreateTime         DateAndTime,
            l3UpdateTime         DateAndTime
        } 
        
    l3IpAddress OBJECT-TYPE 
        SYNTAX       IpAddress
        MAX-ACCESS   read-only
        STATUS       current
        DESCRIPTION "目的IP地址，作为索引。" 
        ::= { l3Entry 1 }
    
    l3NextHopMacAddress OBJECT-TYPE 
        SYNTAX       MacAddress
        MAX-ACCESS   read-only
        STATUS       current
        DESCRIPTION "下一跳IP的MAC地址。" 
        ::= { l3Entry 2 }

    l3Vlan OBJECT-TYPE 
        SYNTAX       VlanIndex
        MAX-ACCESS   read-only
        STATUS       current
        DESCRIPTION "下一跳IP所在的VLAN。" 
        ::= { l3Entry 3 }
    
    l3Port OBJECT-TYPE 
        SYNTAX       INTEGER
        MAX-ACCESS   read-only
        STATUS       current
        DESCRIPTION "报文的出端口。" 
        ::= { l3Entry 4 }

    l3CreateTime OBJECT-TYPE 
        SYNTAX       DateAndTime
        MAX-ACCESS   read-only
        STATUS       current
        DESCRIPTION "Create Time,such as 2004-07-29,13:30:15.0" 
        ::= { l3Entry 5 }

    l3UpdateTime OBJECT-TYPE 
        SYNTAX       DateAndTime
        MAX-ACCESS   read-only
        STATUS       current
        DESCRIPTION "Update Time,such as 2004-07-29,13:30:15.0" 
        ::= { l3Entry 6 }

------------------------------------------------------------------------------
--
--  gbnDeviceSwitchLoopTest - Loop Test Group                    
--
------------------------------------------------------------------------------
   loopTestPortno  OBJECT-TYPE
        SYNTAX     PortList
        MAX-ACCESS read-write
        STATUS current
        DESCRIPTION
            "List of the ports to be tested."
        ::= { gbnDeviceSwitchLoopTest 1 }  

     loopTestType  OBJECT-TYPE
        SYNTAX INTEGER {
               noop(1),    -- no operation
               local(2),   -- for both vdsl and ethernet port
               remote(3),   -- for both vdsl and ethernet port 
               other(4)                   
        } 
        MAX-ACCESS read-write
        STATUS current
        DESCRIPTION
            "DURABLE: { 4 }
             Setting this object to 2-4 enables loop back test.  
             Setting it to 1 disables loop back test."
        ::= { gbnDeviceSwitchLoopTest 2 }  

   loopTestSuccess  OBJECT-TYPE
        SYNTAX PortList
        MAX-ACCESS read-only
        STATUS current
        DESCRIPTION
            "List of ports tested successfully."
        ::= { gbnDeviceSwitchLoopTest 3 }     

------------------------------------------------------------------------------
--
--  gbnDeviceSwitchSRM - SRM Group                    
--
------------------------------------------------------------------------------
    srmHardwareEnable OBJECT-TYPE 
        SYNTAX  INTEGER {
              enabled(1),
              disabled(2)
          }	    
        MAX-ACCESS  read-write
	    STATUS      current
	    DESCRIPTION "Add network routes to hardware table or not.Default is enable." 
	    -- "是否下发网段路由到硬件表中。默认为下发。"
	    ::= { gbnDeviceSwitchSRM 1 }     

   srmHardwareDEFCPU OBJECT-TYPE 
        SYNTAX  INTEGER {
              enabled(1),
              disabled(2)
          }	    
        MAX-ACCESS  read-write
	    STATUS      current
	    DESCRIPTION "The DEF routes goes to CPU." 
	    -- "硬件查找失败的路由发送到CPU，此功能只有TiNet S3750支持，默认为disable"
	    ::= { gbnDeviceSwitchSRM 2 }  
------------------------------------------------------------------------------
--
--  gbnDeviceSwitchFlowAlarm - Port Flow Alarm Group                    
--
------------------------------------------------------------------------------
    portFlowAlarmTable OBJECT-TYPE
        SYNTAX SEQUENCE OF PortFlowAlarmEntry
        MAX-ACCESS not-accessible
        STATUS current
        DESCRIPTION
            "A Table of port flow alarm."
            --端口流量告警表
        ::= { gbnDeviceSwitchFlowAlarm 1 }

    portFlowAlarmEntry OBJECT-TYPE
        SYNTAX PortFlowAlarmEntry
        MAX-ACCESS not-accessible
        STATUS current
        DESCRIPTION
            "A list of port flow alarm."
            --端口流量告警列表
        INDEX { portFlowAlarmPort }
        ::= { portFlowAlarmTable 1 }

    PortFlowAlarmEntry ::= SEQUENCE {
            portFlowAlarmPort            Integer32,            
            portFlowAlarmEnable          TruthValue,
            portFlowAlarmExceedStatus  TruthValue,
            portFlowAlarmExceedThreshold  Integer32,
            portFlowAlarmNormalThreshold  Integer32
        }

    portFlowAlarmPort OBJECT-TYPE
        SYNTAX Integer32 (1..26)
        MAX-ACCESS not-accessible
        STATUS current
        DESCRIPTION
            "The port number."
            --端口号，端口流量告警表的索引值
        ::= { portFlowAlarmEntry 1 }
    
    portFlowAlarmEnable OBJECT-TYPE
        SYNTAX TruthValue
        MAX-ACCESS read-write
        STATUS current
        DESCRIPTION
            "The enable status of the port flow alarm"
            --端口流量告警开启/关闭状态
        ::= { portFlowAlarmEntry 2 }

    portFlowAlarmExceedStatus OBJECT-TYPE
        SYNTAX TruthValue
        MAX-ACCESS read-only
        STATUS current
        DESCRIPTION
            "The exceed status of the port flow alarm"
            --端口流量告警流量状态
        ::= { portFlowAlarmEntry 3 }    

    portFlowAlarmExceedThreshold OBJECT-TYPE
        SYNTAX Integer32
        MAX-ACCESS  read-write
        STATUS current
        DESCRIPTION
            "The exceed threshold of port flow alarm."
            --端口流量过大的阈值
        ::= { portFlowAlarmEntry 4 }        

    portFlowAlarmNormalThreshold OBJECT-TYPE
        SYNTAX  Integer32
        MAX-ACCESS read-write
        STATUS current
        DESCRIPTION
            "The normal threshold of port flow alarm."
            --端口流量正常的阈值
        ::= { portFlowAlarmEntry 5 }   
        
    portFlowAlarmGlobalEnable OBJECT-TYPE
        SYNTAX TruthValue
        MAX-ACCESS read-write
        STATUS current
        DESCRIPTION
            "The global enable status of port flow alarm."
            --全局端口流量告警开启/关闭状态
        ::= { gbnDeviceSwitchFlowAlarm 2 }
            
------------------------------------------------------------------------------
--
--  gbnDeviceSwitchTrap - gbn device switch TRAP                   
--
------------------------------------------------------------------------------
    portFlowAlarmTrap      OBJECT IDENTIFIER ::= { gbnDeviceSwitchFlowAlarm 5 }
    
    portFlowAlarmExceedTrap NOTIFICATION-TYPE
        OBJECTS { portFlowAlarmPort }
        STATUS  current
        DESCRIPTION
               "Port ingress packet rate become too big, port flow exceed alarm happen."
               --如果端口进来的报文速率变得过大，则发出端口速率过大的trap
       	::= { portFlowAlarmTrap 1 }

    portFlowAlarmNormalTrap NOTIFICATION-TYPE
        OBJECTS { portFlowAlarmPort }
        STATUS  current
        DESCRIPTION
               "Port ingress packet rate become normal, port flow normal alarm happen."
               --如果端口进来的报文速率恢复正常，则发出端口速率正常的trap
       	::= { portFlowAlarmTrap 2 }        

   --
   -- the quene-scheduer QOS 
   --
   
   qosQueueSchedulerGroup  OBJECT IDENTIFIER ::= { gbnDeviceSwitchQueneScheduer 1 }
  
   qosWrrQueue1Weight OBJECT-TYPE
       SYNTAX  INTEGER (1..100)   
       ACCESS  read-write
       STATUS  current
       DESCRIPTION
               "Weight of 1th queue(%)."
               --队列1的权重
       ::= { qosQueueSchedulerGroup 1 }   
       
   qosWrrQueue2Weight OBJECT-TYPE
       SYNTAX  INTEGER (1..100)   
       ACCESS  read-write
       STATUS  current
       DESCRIPTION
               "Weight of 2th queue(%). "
               --队列2的权重
       ::= { qosQueueSchedulerGroup 2 }  
       
       
   qosWrrQueue3Weight OBJECT-TYPE
       SYNTAX  INTEGER (1..100)   
       ACCESS  read-write
       STATUS  current
       DESCRIPTION
               "Weight of 3th queue(%)."
               --队列3的权重
       ::= { qosQueueSchedulerGroup 3 }          
       
       
   qosWrrQueue4Weight OBJECT-TYPE
       SYNTAX  INTEGER (1..100)   
       ACCESS  read-write
       STATUS  current
       DESCRIPTION
               "Weight of 4th queue(%)."
               --队列4的权重
       ::= { qosQueueSchedulerGroup 4 }          
       
   qosWrrMaxDelayValue OBJECT-TYPE
       SYNTAX  INTEGER (1..255)   
       ACCESS  read-write
       STATUS  current
       DESCRIPTION
               "the maximum allowable latency for packet transmission on the priorest COS"
               --队列调度时最高优先级的队列最长等待时间
       ::= { qosQueueSchedulerGroup 5 }   
       
   qosQueueSchedulerMode OBJECT-TYPE
       SYNTAX  INTEGER  {
                        strictPriority (1),
                        wrr(2),
                        sp-wrr(3) }                        
       ACCESS  read-write
       STATUS  current
       DESCRIPTION
               "queue scheduler mode: strict priority, weighted round robin" 
               --队列调度模式:绝对优先级、加权轮循调度
       DEFVAL  { strictPriority }
       ::= { qosQueueSchedulerGroup 6 }    

   qosWrrQueue5Weight OBJECT-TYPE
       SYNTAX  INTEGER (1..100)   
       ACCESS  read-write
       STATUS  current
       DESCRIPTION
               "Weight of 5th queue(%)."
               --队列5的权重
       ::= { qosQueueSchedulerGroup 7 }   
       
   qosWrrQueue6Weight OBJECT-TYPE
       SYNTAX  INTEGER (1..100)   
       ACCESS  read-write
       STATUS  current
       DESCRIPTION
               "Weight of 6th queue(%). "
               --队列6的权重
       ::= { qosQueueSchedulerGroup 8 }  
       
       
   qosWrrQueue7Weight OBJECT-TYPE
       SYNTAX  INTEGER (1..100)   
       ACCESS  read-write
       STATUS  current
       DESCRIPTION
               "Weight of 7th queue(%)."
               --队列7的权重
       ::= { qosQueueSchedulerGroup 9 }          
       
       
   qosWrrQueue8Weight OBJECT-TYPE
       SYNTAX  INTEGER (1..100)   
       ACCESS  read-write
       STATUS  current
       DESCRIPTION
               "Weight of 8th queue(%)."
               --队列8的权重
       ::= { qosQueueSchedulerGroup 10 }          
       
   --
   -- the line-rate configuration 
   --
   qosLineRateTable OBJECT-TYPE
       SYNTAX  SEQUENCE OF QosLineRateEntry
       ACCESS  not-accessible
       STATUS  current
       DESCRIPTION
               "A list of line-rate QOS entries. "
               --端口限速入口表
       ::= { gbnDeviceSwitchLineRate 1 }
 
   qosLineRateEntry OBJECT-TYPE
       SYNTAX  QosLineRateEntry
       ACCESS  not-accessible
       STATUS  current
       DESCRIPTION
               "A list of line-rate QOS entries. "
               --端口限速入口
       INDEX   { qosLineRateInterface }
       ::= { qosLineRateTable 1 }
 
   QosLineRateEntry ::=
       SEQUENCE {
           qosLineRateInterface
               INTEGER,                  
           qosLineRateTargetRate
               INTEGER,                  
           qosLineRateRowStatus
               RowStatus                  
       }
 
   qosLineRateInterface OBJECT-TYPE
       SYNTAX  INTEGER (1..26)
       ACCESS  read-only
       STATUS  current
       DESCRIPTION
               "the line rate interface.  "
               --端口限速端口
       ::= { qosLineRateEntry 1 }
       
   qosLineRateTargetRate OBJECT-TYPE
       SYNTAX  INTEGER (1..100)   
       ACCESS  read-write
       STATUS  current
       DESCRIPTION
               "the target rate of the line-rate QOS. "
               --端口限速目标速率
       ::= { qosLineRateEntry 2 }  
       
   --
   -- the port-isolation configuration 
   --
   portIsolationGroup  OBJECT IDENTIFIER ::= { gbnDeviceSwitchPortIsolation 1 }
 
   portIsolationDownLinkPorts OBJECT-TYPE
       SYNTAX  PortList         
       ACCESS  read-write
       STATUS  current
       DESCRIPTION
               "port isolation down link portlist"
               -- 端口隔离的下行端口列表 --
       ::= { portIsolationGroup 1 }  

   --
   -- the storm control 
   --
 
   stormControlTable OBJECT-TYPE
       SYNTAX  SEQUENCE OF StormControlEntry
       ACCESS  not-accessible
       STATUS  current
       DESCRIPTION
               "A list of storm control entries. "
               --风暴控制入口表
       ::= { gbnDeviceSwitchStormControl 1 }
 
   stormControlEntry OBJECT-TYPE
       SYNTAX  StormControlEntry
       ACCESS  not-accessible
       STATUS  current
       DESCRIPTION
               "A list of storm control entries. "
               --风暴控制入口
       INDEX   { stormControlInterface, stormControlType }
       ::= { stormControlTable 1 }
 
   StormControlEntry ::=
       SEQUENCE {
           stormControlInterface
               INTEGER,  
           stormControlType             
               INTEGER,                
           stormControlTargetRate
               INTEGER,                  
           stormControlRowStatus
               RowStatus                  
       }
 
   stormControlInterface OBJECT-TYPE
       SYNTAX  INTEGER (1..26)
       ACCESS  read-only
       STATUS  current
       DESCRIPTION
               "the storm control interface. "
               --风暴控制端口
       ::= { stormControlEntry 1 }
       
   stormControlType OBJECT-TYPE
       SYNTAX  INTEGER   
       ACCESS  read-only
       STATUS  current
       DESCRIPTION
               "the pack flow type of the storm control. "
               --风暴控制报文流类型
       ::= { stormControlEntry 2 } 
           
   stormControlTargetRate OBJECT-TYPE
       SYNTAX  INTEGER (1..1000)   
       ACCESS  read-write
       STATUS  current
       DESCRIPTION
               "the target rate of the storm control. "
               --风暴控制目标速率
       ::= { stormControlEntry 3 }  

   stormControlRowStatus OBJECT-TYPE
        SYNTAX   RowStatus
        MAX-ACCESS   read-write
        STATUS   current 
        DESCRIPTION
                "row status of the storm control"
                --风暴控制行状态
        ::= { stormControlEntry 4 }    	    

--
-- gbnDeviceSwitchAntiDos
--
    ipfragmnetnumber OBJECT-TYPE
        SYNTAX INTEGER (0..800)
        MAX-ACCESS read-write
        STATUS current
        DESCRIPTION
            "The ip fragment number."
        --IP分片报文的处理数目.默认为800,取值为0到800,当为0的时候不处理分片报文. 
        ::= { gbnDeviceSwitchAntiDos 1 }  
        
    ipTTL  OBJECT-TYPE
        SYNTAX TruthValue
        MAX-ACCESS read-write
        STATUS current
        DESCRIPTION
           "Control IP with TTL=0 packet,default is not traffic  to the  CPU."
         --控制TTL=0的报文是否送往CPU,默认情况是关闭上报CPU.
         ::= { gbnDeviceSwitchAntiDos 2 } 
--
-- the bandwidth control 
--
   
   bandwidthcontrolTable OBJECT-TYPE
        SYNTAX SEQUENCE OF BandwidthcontrolEntry
        MAX-ACCESS read-only
        STATUS current
        DESCRIPTION
            "A table of switch interfaces and associated properties."
        ::= { gbnDeviceSwitchBandWidth 1 }
 
    bandwidthcontrolEntry OBJECT-TYPE
        SYNTAX BandwidthcontrolEntry
        MAX-ACCESS not-accessible
        STATUS current
        DESCRIPTION
            "Table entry for switch interface control and status information."
        INDEX { controlPort }
        ::= { bandwidthcontrolTable 1 }

    BandwidthcontrolEntry ::= SEQUENCE {
        controlPort                    INTEGER,
        portEgressBandwidthcontrol     INTEGER,
        portIngressBandwidthcontrol    INTEGER
      }

    controlPort OBJECT-TYPE
        SYNTAX INTEGER (1..26)
        MAX-ACCESS not-accessible
        STATUS current
        DESCRIPTION
            "the index of port."
        ::= { bandwidthcontrolEntry 1 }

    portEgressBandwidthcontrol OBJECT-TYPE
        SYNTAX INTEGER (0..1024000)
        MAX-ACCESS read-write
        STATUS current
        DESCRIPTION
            "Egress Speed Value of port, bandwidth control ."
        ::= { bandwidthcontrolEntry 2 }

    portIngressBandwidthcontrol OBJECT-TYPE
        SYNTAX INTEGER (0..1024000)
        MAX-ACCESS read-write
        STATUS current
        DESCRIPTION
            "Ingress Speed Value of port, bandwidth control ."
        ::= { bandwidthcontrolEntry 3 }

--
-- END of gbnDeviceSwitch-MIB               
--

END
