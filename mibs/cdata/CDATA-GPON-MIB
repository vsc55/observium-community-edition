--
-- CDATA-GPON-MIB.my
-- MIB generated by MG-SOFT Visual MIB Builder Version 6.0  Build 88
-- Tuesday, January 25, 2022 at 17:28:25
--

	CDATA-GPON-MIB DEFINITIONS ::= BEGIN
 
		IMPORTS
			gpon			
				FROM CDATA-COMMON-SMI
			OBJECT-GROUP, MODULE-COMPLIANCE, NOTIFICATION-GROUP			
				FROM SNMPv2-CONF			
			sysDescr, sysObjectID, sysUpTime, sysContact, sysName, 
			sysLocation, sysServices, sysORLastChange, sysORIndex, sysORID, 
			sysORDescr, sysORUpTime, snmpInPkts, snmpOutPkts, snmpInBadVersions, 
			snmpInBadCommunityNames, snmpInBadCommunityUses, snmpInASNParseErrs, snmpInTooBigs, snmpInNoSuchNames, 
			snmpInBadValues, snmpInReadOnlys, snmpInGenErrs, snmpInTotalReqVars, snmpInTotalSetVars, 
			snmpInGetRequests, snmpInGetNexts, snmpInSetRequests, snmpInGetResponses, snmpInTraps, 
			snmpOutTooBigs, snmpOutNoSuchNames, snmpOutBadValues, snmpOutGenErrs, snmpOutGetRequests, 
			snmpOutGetNexts, snmpOutSetRequests, snmpOutGetResponses, snmpOutTraps, snmpEnableAuthenTraps, 
			snmpSilentDrops, snmpProxyDrops, snmpTrapOID, snmpTrapEnterprise, coldStart, 
			warmStart, authenticationFailure, snmpSetSerialNo, snmpBasicCompliance, snmpSetGroup, 
			systemGroup, snmpBasicNotificationsGroup, snmpGroup, snmpCommunityGroup, snmpObsoleteGroup			
				FROM SNMPv2-MIB			
			IpAddress, Integer32, Unsigned32, BITS, OBJECT-TYPE, 
			MODULE-IDENTITY, NOTIFICATION-TYPE			
				FROM SNMPv2-SMI			
			DisplayString, RowStatus, TEXTUAL-CONVENTION			
				FROM SNMPv2-TC;
	
	
		-- 1.3.6.1.4.1.34592.1.5.1
		gponMIB MODULE-IDENTITY 
			LAST-UPDATED "201603021606Z"		-- March 02, 2016 at 16:06 GMT
			ORGANIZATION 
				"Organization."
			CONTACT-INFO 
				"Contact-info."
			DESCRIPTION 
				"Description."
			::= { gpon 1 }

		
	
--
-- Textual conventions
--
	
		GponDbaProfileId ::= TEXTUAL-CONVENTION
			STATUS current
			DESCRIPTION 
				"Description."
			SYNTAX Integer32 (0..128 | 65535)

		GponDbaProfileName ::= TEXTUAL-CONVENTION
			STATUS current
			DESCRIPTION 
				"Description."
			SYNTAX OCTET STRING (SIZE (1..16))

		GponLinePorfileId ::= TEXTUAL-CONVENTION
			STATUS current
			DESCRIPTION 
				"Description."
			SYNTAX Integer32 (0..512)

		GponLinePorfileName ::= TEXTUAL-CONVENTION
			STATUS current
			DESCRIPTION 
				"Description."
			SYNTAX OCTET STRING (SIZE (1..32))

		GponLinePorfileTcontId ::= TEXTUAL-CONVENTION
			STATUS current
			DESCRIPTION 
				"Description."
			SYNTAX Integer32 (1..3 | 65535)

		GponLinePorfileGemId ::= TEXTUAL-CONVENTION
			STATUS current
			DESCRIPTION 
				"Description."
			SYNTAX Integer32 (1..24)

		GponLinePorfileGemMapId ::= TEXTUAL-CONVENTION
			STATUS current
			DESCRIPTION 
				"Description."
			SYNTAX Integer32 (1..8)

		GponVlanPriority ::= TEXTUAL-CONVENTION
			STATUS current
			DESCRIPTION 
				"Description."
			SYNTAX Integer32 (0..7)

		GponSrvProfileId ::= TEXTUAL-CONVENTION
			STATUS current
			DESCRIPTION 
				"Description."
			SYNTAX Integer32 (0..512)

		GponSrvProfileName ::= TEXTUAL-CONVENTION
			STATUS current
			DESCRIPTION 
				"Description."
			SYNTAX OCTET STRING (SIZE (1..16))

		GponVlanId ::= TEXTUAL-CONVENTION
			STATUS current
			DESCRIPTION 
				"Description."
			SYNTAX Integer32 (1..4094)

		GponTrafficProfileId ::= TEXTUAL-CONVENTION
			STATUS current
			DESCRIPTION 
				"Description."
			SYNTAX Integer32 (1..256)

		GponTrafficProfileName ::= TEXTUAL-CONVENTION
			STATUS current
			DESCRIPTION 
				"Description."
			SYNTAX OCTET STRING (SIZE (1..32))

		GponSipAgentProfileId ::= TEXTUAL-CONVENTION
			STATUS current
			DESCRIPTION 
				"Description."
			SYNTAX Integer32 (0..16 | 65535)

		GponSipAgentProfileName ::= TEXTUAL-CONVENTION
			STATUS current
			DESCRIPTION 
				"Description."
			SYNTAX OCTET STRING (SIZE (1..32))

		GponSipUri ::= TEXTUAL-CONVENTION
			STATUS current
			DESCRIPTION 
				"Description."
			SYNTAX OCTET STRING (SIZE (1..63))

		GponSipRightFlagProfileId ::= TEXTUAL-CONVENTION
			STATUS current
			DESCRIPTION 
				"Description."
			SYNTAX Integer32 (0..16 | 65535)

		GponSipRightFlagProfileName ::= TEXTUAL-CONVENTION
			STATUS current
			DESCRIPTION 
				"Description."
			SYNTAX OCTET STRING (SIZE (1..32))

		GponSwitch ::= TEXTUAL-CONVENTION
			STATUS current
			DESCRIPTION 
				"Description."
			SYNTAX INTEGER
				{
				enable(1),
				disable(2)
				}

		GponDigitMapProfileId ::= TEXTUAL-CONVENTION
			STATUS current
			DESCRIPTION 
				"Description."
			SYNTAX Integer32 (0..16 | 65535)

		GponPotsProfileId ::= TEXTUAL-CONVENTION
			STATUS current
			DESCRIPTION 
				"Description."
			SYNTAX Integer32 (0..16 | 65535)


		GponDeviceId ::= TEXTUAL-CONVENTION
			STATUS current
			DESCRIPTION 
				"Description."
			SYNTAX Integer32 (1..8)

		GponCardId ::= TEXTUAL-CONVENTION
			STATUS current
			DESCRIPTION 
				"Description."
			SYNTAX Integer32 (0..8)

		GponOltPortId ::= TEXTUAL-CONVENTION
			STATUS current
			DESCRIPTION 
				"Description."
			SYNTAX Integer32

		GponOltAutoAuthRuleId ::= TEXTUAL-CONVENTION
			STATUS current
			DESCRIPTION 
				"Description."
			SYNTAX Integer32 (1..20)

		GponOnuId ::= TEXTUAL-CONVENTION
			STATUS current
			DESCRIPTION 
				"Description."
			SYNTAX Integer32 (1..128)

		GponOnuSn ::= TEXTUAL-CONVENTION
			STATUS current
			DESCRIPTION 
				"Description."
			SYNTAX OCTET STRING (SIZE (12))

		GponOnuPassword ::= TEXTUAL-CONVENTION
			STATUS current
			DESCRIPTION 
				"Description."
			SYNTAX OCTET STRING (SIZE (1..10))

		GponOnuLoid ::= TEXTUAL-CONVENTION
			STATUS current
			DESCRIPTION 
				"Description."
			SYNTAX OCTET STRING (SIZE (1..24))

		GponOnuLoidPassword ::= TEXTUAL-CONVENTION
			STATUS current
			DESCRIPTION 
				"Description."
			SYNTAX OCTET STRING (SIZE (1..12))

		GponOnuEthPortId ::= TEXTUAL-CONVENTION
			STATUS current
			DESCRIPTION 
				"Description."
			SYNTAX Integer32 (1..8)
		GponMac ::= TEXTUAL-CONVENTION
			STATUS current
			DESCRIPTION 
				"Description."
			SYNTAX OCTET STRING (SIZE (6))

		GponOnuPotsPortId ::= TEXTUAL-CONVENTION
			STATUS current
			DESCRIPTION 
				"Description."
			SYNTAX Integer32 (1..8)

		GponTr069ProfileId ::= TEXTUAL-CONVENTION
			STATUS current
			DESCRIPTION 
				"Description."
			SYNTAX Integer32 (1..32)

	
--
-- Node definitions
--
	
		-- 1.3.6.1.4.1.34592.1.5.1.1
		gponObjects OBJECT IDENTIFIER ::= { gponMIB 1 }

		
		-- 1.3.6.1.4.1.34592.1.5.1.1.1
		gponProfileObjects OBJECT IDENTIFIER ::= { gponObjects 1 }

		
		-- 1.3.6.1.4.1.34592.1.5.1.1.1.2
		gponDbaProfileObjects OBJECT IDENTIFIER ::= { gponProfileObjects 2 }

		
		-- 1.3.6.1.4.1.34592.1.5.1.1.1.2.1
		gponDbaProfileInfoTable OBJECT-TYPE
			SYNTAX SEQUENCE OF GponDbaProfileInfoEntry
			MAX-ACCESS not-accessible
			STATUS current
			DESCRIPTION
				"Description."
			::= { gponDbaProfileObjects 1 }

		
		-- 1.3.6.1.4.1.34592.1.5.1.1.1.2.1.1
		gponDbaProfileInfoEntry OBJECT-TYPE
			SYNTAX GponDbaProfileInfoEntry
			MAX-ACCESS not-accessible
			STATUS current
			DESCRIPTION
				"Description."
			INDEX { gponDbaProfileId }
			::= { gponDbaProfileInfoTable 1 }

		
		GponDbaProfileInfoEntry ::=
			SEQUENCE { 
				gponDbaProfileId
					GponDbaProfileId,
				gponDbaProfileRowStatus
					RowStatus,
				gponDbaProfileName
					GponDbaProfileName,
				gponDbaProfileBindNum
					Integer32
			 }

		-- 1.3.6.1.4.1.34592.1.5.1.1.1.2.1.1.1
		gponDbaProfileId OBJECT-TYPE
			SYNTAX GponDbaProfileId
			MAX-ACCESS not-accessible
			STATUS current
			DESCRIPTION
				"Dba profile index,
				1-128:user dba profile
				65535:default dba profile, profile id is 0
				"
			::= { gponDbaProfileInfoEntry 1 }

		
		-- 1.3.6.1.4.1.34592.1.5.1.1.1.2.1.1.2
		gponDbaProfileRowStatus OBJECT-TYPE
			SYNTAX RowStatus
			MAX-ACCESS read-create
			STATUS current
			DESCRIPTION
				"Row status. This object is used to differentiate the creation, modification and deletion operations for an object."
			::= { gponDbaProfileInfoEntry 2 }

		
		-- 1.3.6.1.4.1.34592.1.5.1.1.1.2.1.1.3
		gponDbaProfileName OBJECT-TYPE
			SYNTAX GponDbaProfileName
			MAX-ACCESS read-create
			STATUS current
			DESCRIPTION
				"Description."
			::= { gponDbaProfileInfoEntry 3 }

		
		-- 1.3.6.1.4.1.34592.1.5.1.1.1.2.1.1.4
		gponDbaProfileBindNum OBJECT-TYPE
			SYNTAX Integer32
			MAX-ACCESS read-only
			STATUS current
			DESCRIPTION
				"Number of bound DBA profiles."
			::= { gponDbaProfileInfoEntry 4 }

		
		-- 1.3.6.1.4.1.34592.1.5.1.1.1.2.2
		gponDbaProfileCfgTable OBJECT-TYPE
			SYNTAX SEQUENCE OF GponDbaProfileCfgEntry
			MAX-ACCESS not-accessible
			STATUS current
			DESCRIPTION
				"Description."
			::= { gponDbaProfileObjects 2 }

		
		-- 1.3.6.1.4.1.34592.1.5.1.1.1.2.2.1
		gponDbaProfileCfgEntry OBJECT-TYPE
			SYNTAX GponDbaProfileCfgEntry
			MAX-ACCESS not-accessible
			STATUS current
			DESCRIPTION
				"Description."
			INDEX { gponDbaProfileId }
			::= { gponDbaProfileCfgTable 1 }

		
		GponDbaProfileCfgEntry ::=
			SEQUENCE { 
				gponDbaProfileType
					INTEGER,
				gponDbaProfileFixRate
					Integer32,
				gponDbaProfileAssureRate
					Integer32,
				gponDbaProfileMaxRate
					Integer32
			 }

		-- 1.3.6.1.4.1.34592.1.5.1.1.1.2.2.1.1
		gponDbaProfileType OBJECT-TYPE
			SYNTAX INTEGER
				{
				fix(1),
				assure(2),
				assureAndMax(3),
				max(4),
				fixAndAssureAndMax(5)
				}
			MAX-ACCESS read-write
			STATUS current
			DESCRIPTION
				"The DBA type index."
			::= { gponDbaProfileCfgEntry 1 }

		
		-- 1.3.6.1.4.1.34592.1.5.1.1.1.2.2.1.2
		gponDbaProfileFixRate OBJECT-TYPE
			SYNTAX Integer32 (0 | 128..1060864)
			UNITS "kbps"
			MAX-ACCESS read-write
			STATUS current
			DESCRIPTION
				"Fixed bandwidth of the profile."
			::= { gponDbaProfileCfgEntry 2 }

		
		-- 1.3.6.1.4.1.34592.1.5.1.1.1.2.2.1.3
		gponDbaProfileAssureRate OBJECT-TYPE
			SYNTAX Integer32 (0 | 256..1060864)
			UNITS "kbps"
			MAX-ACCESS read-write
			STATUS current
			DESCRIPTION
				"Assured bandwidth of the profile."
			::= { gponDbaProfileCfgEntry 3 }

		
		-- 1.3.6.1.4.1.34592.1.5.1.1.1.2.2.1.4
		gponDbaProfileMaxRate OBJECT-TYPE
			SYNTAX Integer32 (0 | 128..1274880)
			UNITS "kbps"
			MAX-ACCESS read-write
			STATUS current
			DESCRIPTION
				"Max bandwidth of the profile."
			::= { gponDbaProfileCfgEntry 4 }

		
		-- 1.3.6.1.4.1.34592.1.5.1.1.1.2.3
		gponDbaProfileBindInfoTable OBJECT-TYPE
			SYNTAX SEQUENCE OF GponDbaProfileBindInfoEntry
			MAX-ACCESS not-accessible
			STATUS current
			DESCRIPTION
				"Description."
			::= { gponDbaProfileObjects 3 }

		
		-- 1.3.6.1.4.1.34592.1.5.1.1.1.2.3.1
		gponDbaProfileBindInfoEntry OBJECT-TYPE
			SYNTAX GponDbaProfileBindInfoEntry
			MAX-ACCESS not-accessible
			STATUS current
			DESCRIPTION
				"Description."
			INDEX { gponDbaProfileId, gponLineProfileId }
			::= { gponDbaProfileBindInfoTable 1 }

		
		GponDbaProfileBindInfoEntry ::=
			SEQUENCE { 
				gponDbaProfileBindLineProfileTcontList
					DisplayString
			 }

		-- 1.3.6.1.4.1.34592.1.5.1.1.1.2.3.1.2
		gponDbaProfileBindLineProfileTcontList OBJECT-TYPE
			SYNTAX DisplayString
			MAX-ACCESS read-only
			STATUS current
			DESCRIPTION
				"Description."
			::= { gponDbaProfileBindInfoEntry 2 }

		
		-- 1.3.6.1.4.1.34592.1.5.1.1.1.3
		gponLineProfileObjects OBJECT IDENTIFIER ::= { gponProfileObjects 3 }

		
		-- 1.3.6.1.4.1.34592.1.5.1.1.1.3.1
		gponLineProfileInfoTable OBJECT-TYPE
			SYNTAX SEQUENCE OF GponLineProfileInfoEntry
			MAX-ACCESS not-accessible
			STATUS current
			DESCRIPTION
				"Description."
			::= { gponLineProfileObjects 1 }

		
		-- 1.3.6.1.4.1.34592.1.5.1.1.1.3.1.1
		gponLineProfileInfoEntry OBJECT-TYPE
			SYNTAX GponLineProfileInfoEntry
			MAX-ACCESS not-accessible
			STATUS current
			DESCRIPTION
				"Description."
			INDEX { gponLineProfileId }
			::= { gponLineProfileInfoTable 1 }

		
		GponLineProfileInfoEntry ::=
			SEQUENCE { 
				gponLineProfileId
					GponLinePorfileId,
				gponLineProfileRowStatus
					RowStatus,
				gponLineProfileName
					GponLinePorfileName,
				gponLineProfileMappingMode
					INTEGER,
				gponLineProfileTcontNum
					Integer32,
				gponLineProfileGemNum
					Integer32,
				gponLineProfileBindNum
					Integer32
			 }

		-- 1.3.6.1.4.1.34592.1.5.1.1.1.3.1.1.1
		gponLineProfileId OBJECT-TYPE
			SYNTAX GponLinePorfileId
			MAX-ACCESS not-accessible
			STATUS current
			DESCRIPTION
				"Line profile index,
				1-512:user line profile
				65535:default line profile, it is reserve."
			::= { gponLineProfileInfoEntry 1 }

		
		-- 1.3.6.1.4.1.34592.1.5.1.1.1.3.1.1.2
		gponLineProfileRowStatus OBJECT-TYPE
			SYNTAX RowStatus
			MAX-ACCESS read-create
			STATUS current
			DESCRIPTION
				"Description."
			::= { gponLineProfileInfoEntry 2 }

		
		-- 1.3.6.1.4.1.34592.1.5.1.1.1.3.1.1.3
		gponLineProfileName OBJECT-TYPE
			SYNTAX GponLinePorfileName
			MAX-ACCESS read-create
			STATUS current
			DESCRIPTION
				"Description."
			::= { gponLineProfileInfoEntry 3 }

		
		-- 1.3.6.1.4.1.34592.1.5.1.1.1.3.1.1.4
		gponLineProfileMappingMode OBJECT-TYPE
			SYNTAX INTEGER
				{
				vlan(1),
				priority(2),
				vlanAndPriority(3)
				}
			MAX-ACCESS read-create
			STATUS current
			DESCRIPTION
				"Description."
			::= { gponLineProfileInfoEntry 4 }

		
		-- 1.3.6.1.4.1.34592.1.5.1.1.1.3.1.1.5
		gponLineProfileTcontNum OBJECT-TYPE
			SYNTAX Integer32
			MAX-ACCESS read-only
			STATUS current
			DESCRIPTION
				"Description."
			::= { gponLineProfileInfoEntry 5 }

		
		-- 1.3.6.1.4.1.34592.1.5.1.1.1.3.1.1.6
		gponLineProfileGemNum OBJECT-TYPE
			SYNTAX Integer32
			MAX-ACCESS read-only
			STATUS current
			DESCRIPTION
				"Description."
			::= { gponLineProfileInfoEntry 6 }

		
		-- 1.3.6.1.4.1.34592.1.5.1.1.1.3.1.1.7
		gponLineProfileBindNum OBJECT-TYPE
			SYNTAX Integer32
			MAX-ACCESS read-only
			STATUS current
			DESCRIPTION
				"Description."
			::= { gponLineProfileInfoEntry 7 }

		
		-- 1.3.6.1.4.1.34592.1.5.1.1.1.3.2
		gponLineProfileTcontTable OBJECT-TYPE
			SYNTAX SEQUENCE OF GponLineProfileTcontEntry
			MAX-ACCESS not-accessible
			STATUS current
			DESCRIPTION
				"Description."
			::= { gponLineProfileObjects 2 }

		
		-- 1.3.6.1.4.1.34592.1.5.1.1.1.3.2.1
		gponLineProfileTcontEntry OBJECT-TYPE
			SYNTAX GponLineProfileTcontEntry
			MAX-ACCESS not-accessible
			STATUS current
			DESCRIPTION
				"Description."
			INDEX { gponLineProfileId, gponLineProfileTcontId }
			::= { gponLineProfileTcontTable 1 }

		
		GponLineProfileTcontEntry ::=
			SEQUENCE { 
				gponLineProfileTcontId
					GponLinePorfileTcontId,
				gponLineProfileTcontRowStatus
					RowStatus,
				gponLineProfileTcontDbaProfileId
					Integer32
			 }

		-- 1.3.6.1.4.1.34592.1.5.1.1.1.3.2.1.1
		gponLineProfileTcontId OBJECT-TYPE
			SYNTAX GponLinePorfileTcontId
			MAX-ACCESS not-accessible
			STATUS current
			DESCRIPTION
				"Description."
			::= { gponLineProfileTcontEntry 1 }

		
		-- 1.3.6.1.4.1.34592.1.5.1.1.1.3.2.1.2
		gponLineProfileTcontRowStatus OBJECT-TYPE
			SYNTAX RowStatus
			MAX-ACCESS read-create
			STATUS current
			DESCRIPTION
				"Description."
			::= { gponLineProfileTcontEntry 2 }

		
		-- 1.3.6.1.4.1.34592.1.5.1.1.1.3.2.1.3
		gponLineProfileTcontDbaProfileId OBJECT-TYPE
			SYNTAX Integer32 (1..128 | 65535)
			MAX-ACCESS read-create
			STATUS current
			DESCRIPTION
				"Description."
			::= { gponLineProfileTcontEntry 3 }

		
		-- 1.3.6.1.4.1.34592.1.5.1.1.1.3.3
		gponLineProfileGemTable OBJECT-TYPE
			SYNTAX SEQUENCE OF GponLineProfileGemEntry
			MAX-ACCESS not-accessible
			STATUS current
			DESCRIPTION
				"Description."
			::= { gponLineProfileObjects 3 }

		
		-- 1.3.6.1.4.1.34592.1.5.1.1.1.3.3.1
		gponLineProfileGemEntry OBJECT-TYPE
			SYNTAX GponLineProfileGemEntry
			MAX-ACCESS not-accessible
			STATUS current
			DESCRIPTION
				"Description."
			INDEX { gponLineProfileId, gponLineProfileGemId }
			::= { gponLineProfileGemTable 1 }

		
		GponLineProfileGemEntry ::=
			SEQUENCE { 
				gponLineProfileGemId
					GponLinePorfileGemId,
				gponLineProfileGemRowStatus
					RowStatus,
				gponLineProfileGemTcontId
					Integer32,
				gponLineProfileGemUpCar
					Integer32,
				gponLineProfileGemDownCar
					Integer32,
				gponLineProfileGemMapNum
					Integer32
			 }

		-- 1.3.6.1.4.1.34592.1.5.1.1.1.3.3.1.1
		gponLineProfileGemId OBJECT-TYPE
			SYNTAX GponLinePorfileGemId
			MAX-ACCESS read-write
			STATUS current
			DESCRIPTION
				"Description."
			::= { gponLineProfileGemEntry 1 }

		
		-- 1.3.6.1.4.1.34592.1.5.1.1.1.3.3.1.2
		gponLineProfileGemRowStatus OBJECT-TYPE
			SYNTAX RowStatus
			MAX-ACCESS read-create
			STATUS current
			DESCRIPTION
				"Description."
			::= { gponLineProfileGemEntry 2 }

		
		-- 1.3.6.1.4.1.34592.1.5.1.1.1.3.3.1.3
		gponLineProfileGemTcontId OBJECT-TYPE
			SYNTAX Integer32 (1..3)
			MAX-ACCESS read-create
			STATUS current
			DESCRIPTION
				"Description."
			::= { gponLineProfileGemEntry 3 }

		
		-- 1.3.6.1.4.1.34592.1.5.1.1.1.3.3.1.4
		gponLineProfileGemUpCar OBJECT-TYPE
			SYNTAX Integer32 (1..256)
			MAX-ACCESS read-create
			STATUS current
			DESCRIPTION
				"Description."
			::= { gponLineProfileGemEntry 4 }

		
		-- 1.3.6.1.4.1.34592.1.5.1.1.1.3.3.1.5
		gponLineProfileGemDownCar OBJECT-TYPE
			SYNTAX Integer32 (1..256)
			MAX-ACCESS read-create
			STATUS current
			DESCRIPTION
				"Description."
			::= { gponLineProfileGemEntry 5 }

		
		-- 1.3.6.1.4.1.34592.1.5.1.1.1.3.3.1.6
		gponLineProfileGemMapNum OBJECT-TYPE
			SYNTAX Integer32
			MAX-ACCESS read-only
			STATUS current
			DESCRIPTION
				"Description."
			::= { gponLineProfileGemEntry 6 }

		
		-- 1.3.6.1.4.1.34592.1.5.1.1.1.3.4
		gponLineProfileGemMapTable OBJECT-TYPE
			SYNTAX SEQUENCE OF GponLineProfileGemMapEntry
			MAX-ACCESS not-accessible
			STATUS current
			DESCRIPTION
				"Description."
			::= { gponLineProfileObjects 4 }

		
		-- 1.3.6.1.4.1.34592.1.5.1.1.1.3.4.1
		gponLineProfileGemMapEntry OBJECT-TYPE
			SYNTAX GponLineProfileGemMapEntry
			MAX-ACCESS not-accessible
			STATUS current
			DESCRIPTION
				"Description."
			INDEX { gponLineProfileId, gponLineProfileGemId, gponLineProfileGemMapId }
			::= { gponLineProfileGemMapTable 1 }

		
		GponLineProfileGemMapEntry ::=
			SEQUENCE { 
				gponLineProfileGemMapId
					GponLinePorfileGemMapId,
				gponLineProfileGemMapRowStatus
					RowStatus,
				gponLineProfileGemMapVlan
					INTEGER,
				gponLineProfileGemMapPriority
					GponVlanPriority
			 }

		-- 1.3.6.1.4.1.34592.1.5.1.1.1.3.4.1.1
		gponLineProfileGemMapId OBJECT-TYPE
			SYNTAX GponLinePorfileGemMapId
			MAX-ACCESS not-accessible
			STATUS current
			DESCRIPTION
				"Description."
			::= { gponLineProfileGemMapEntry 1 }

		
		-- 1.3.6.1.4.1.34592.1.5.1.1.1.3.4.1.2
		gponLineProfileGemMapRowStatus OBJECT-TYPE
			SYNTAX RowStatus
			MAX-ACCESS read-create
			STATUS current
			DESCRIPTION
				"Description."
			::= { gponLineProfileGemMapEntry 2 }

		
		-- 1.3.6.1.4.1.34592.1.5.1.1.1.3.4.1.3
		gponLineProfileGemMapVlan OBJECT-TYPE
			SYNTAX INTEGER (1..4094)
			MAX-ACCESS read-create
			STATUS current
			DESCRIPTION
				"Description."
			::= { gponLineProfileGemMapEntry 3 }

		
		-- 1.3.6.1.4.1.34592.1.5.1.1.1.3.4.1.4
		gponLineProfileGemMapPriority OBJECT-TYPE
			SYNTAX GponVlanPriority
			MAX-ACCESS read-create
			STATUS current
			DESCRIPTION
				"Description."
			::= { gponLineProfileGemMapEntry 4 }

		
		-- 1.3.6.1.4.1.34592.1.5.1.1.1.3.5
		gponLineProfileBindInfoTable OBJECT-TYPE
			SYNTAX SEQUENCE OF GponLineProfileBindInfoEntry
			MAX-ACCESS not-accessible
			STATUS current
			DESCRIPTION
				"Description."
			::= { gponLineProfileObjects 5 }

		
		-- 1.3.6.1.4.1.34592.1.5.1.1.1.3.5.1
		gponLineProfileBindInfoEntry OBJECT-TYPE
			SYNTAX GponLineProfileBindInfoEntry
			MAX-ACCESS not-accessible
			STATUS current
			DESCRIPTION
				"Description."
			INDEX { gponLineProfileId, gponOltDeviceId, gponOltCardId, gponOltPortId }
			::= { gponLineProfileBindInfoTable 1 }

		
		GponLineProfileBindInfoEntry ::=
			SEQUENCE { 
				gponLineProfileBindOnuList
					DisplayString
			 }

		-- 1.3.6.1.4.1.34592.1.5.1.1.1.3.5.1.2
		gponLineProfileBindOnuList OBJECT-TYPE
			SYNTAX DisplayString
			MAX-ACCESS read-only
			STATUS current
			DESCRIPTION
				"Description."
			::= { gponLineProfileBindInfoEntry 2 }

		
		-- 1.3.6.1.4.1.34592.1.5.1.1.1.4
		gponSrvProfileObjects OBJECT IDENTIFIER ::= { gponProfileObjects 4 }

		
		-- 1.3.6.1.4.1.34592.1.5.1.1.1.4.1
		gponSrvProfileInfoTable OBJECT-TYPE
			SYNTAX SEQUENCE OF GponSrvProfileInfoEntry
			MAX-ACCESS not-accessible
			STATUS current
			DESCRIPTION
				"Description."
			::= { gponSrvProfileObjects 1 }

		
		-- 1.3.6.1.4.1.34592.1.5.1.1.1.4.1.1
		gponSrvProfileInfoEntry OBJECT-TYPE
			SYNTAX GponSrvProfileInfoEntry
			MAX-ACCESS not-accessible
			STATUS current
			DESCRIPTION
				"Description."
			INDEX { gponSrvProfileId }
			::= { gponSrvProfileInfoTable 1 }

		
		GponSrvProfileInfoEntry ::=
			SEQUENCE { 
				gponSrvProfileId
					GponSrvProfileId,
				gponSrvProfileRowStatus
					RowStatus,
				gponSrvProfileName
					GponSrvProfileName,
				gponSrvProfileBindNum
					Integer32
			 }

		-- 1.3.6.1.4.1.34592.1.5.1.1.1.4.1.1.1
		gponSrvProfileId OBJECT-TYPE
			SYNTAX GponSrvProfileId
			MAX-ACCESS read-write
			STATUS current
			DESCRIPTION
				"Description."
			::= { gponSrvProfileInfoEntry 1 }

		
		-- 1.3.6.1.4.1.34592.1.5.1.1.1.4.1.1.2
		gponSrvProfileRowStatus OBJECT-TYPE
			SYNTAX RowStatus
			MAX-ACCESS read-create
			STATUS current
			DESCRIPTION
				"Description."
			::= { gponSrvProfileInfoEntry 2 }

		
		-- 1.3.6.1.4.1.34592.1.5.1.1.1.4.1.1.3
		gponSrvProfileName OBJECT-TYPE
			SYNTAX GponSrvProfileName
			MAX-ACCESS read-create
			STATUS current
			DESCRIPTION
				"Description."
			::= { gponSrvProfileInfoEntry 3 }

		
		-- 1.3.6.1.4.1.34592.1.5.1.1.1.4.1.1.8
		gponSrvProfileBindNum OBJECT-TYPE
			SYNTAX Integer32
			MAX-ACCESS read-only
			STATUS current
			DESCRIPTION
				"Description."
			::= { gponSrvProfileInfoEntry 8 }

		
		-- 1.3.6.1.4.1.34592.1.5.1.1.1.4.2
		gponSrvProfileCfgTable OBJECT-TYPE
			SYNTAX SEQUENCE OF GponSrvProfileCfgEntry
			MAX-ACCESS not-accessible
			STATUS current
			DESCRIPTION
				"Description."
			::= { gponSrvProfileObjects 2 }

		
		-- 1.3.6.1.4.1.34592.1.5.1.1.1.4.2.1
		gponSrvProfileCfgEntry OBJECT-TYPE
			SYNTAX GponSrvProfileCfgEntry
			MAX-ACCESS not-accessible
			STATUS current
			DESCRIPTION
				"Description."
			INDEX { gponSrvProfileId }
			::= { gponSrvProfileCfgTable 1 }

		
		GponSrvProfileCfgEntry ::=
			SEQUENCE { 
				gponSrvProfileMcMode
					INTEGER,
				gponSrvProfileUpIgmpFwdMode
					INTEGER,
				gponSrvProfileUpIgmpTCI
					Integer32,
				gponSrvProfileDnMcMode
					INTEGER,
				gponSrvProfileDnMcTCI
					Integer32
			 }

		-- 1.3.6.1.4.1.34592.1.5.1.1.1.4.2.1.1
		gponSrvProfileMcMode OBJECT-TYPE
			SYNTAX INTEGER
				{
				igmp-snooping(0),
				igmp-snooping-proxy(1),
				igmp-proxy(2)
				}
			MAX-ACCESS read-write
			STATUS current
			DESCRIPTION
				"Description."
			::= { gponSrvProfileCfgEntry 1 }

		
		-- 1.3.6.1.4.1.34592.1.5.1.1.1.4.2.1.2
		gponSrvProfileUpIgmpFwdMode OBJECT-TYPE
			SYNTAX INTEGER
				{
				transparent(0),
				default(1),
				translation(2)
				}
			MAX-ACCESS read-write
			STATUS current
			DESCRIPTION
				"Description."
			::= { gponSrvProfileCfgEntry 2 }

		
		-- 1.3.6.1.4.1.34592.1.5.1.1.1.4.2.1.3
		gponSrvProfileUpIgmpTCI OBJECT-TYPE
			SYNTAX Integer32
			MAX-ACCESS read-write
			STATUS current
			DESCRIPTION
				"Description."
			::= { gponSrvProfileCfgEntry 3 }

		
		-- 1.3.6.1.4.1.34592.1.5.1.1.1.4.2.1.4
		gponSrvProfileDnMcMode OBJECT-TYPE
			SYNTAX INTEGER
				{
				transparent(0),
				untag(1),
				translation(2)
				}
			MAX-ACCESS read-write
			STATUS current
			DESCRIPTION
				"Description."
			::= { gponSrvProfileCfgEntry 4 }

		
		-- 1.3.6.1.4.1.34592.1.5.1.1.1.4.2.1.5
		gponSrvProfileDnMcTCI OBJECT-TYPE
			SYNTAX Integer32
			MAX-ACCESS read-write
			STATUS current
			DESCRIPTION
				"Description."
			::= { gponSrvProfileCfgEntry 5 }

		
		-- 1.3.6.1.4.1.34592.1.5.1.1.1.4.3
		gponSrvProfilePortNumTable OBJECT-TYPE
			SYNTAX SEQUENCE OF GponSrvProfilePortNumEntry
			MAX-ACCESS not-accessible
			STATUS current
			DESCRIPTION
				"Description."
			::= { gponSrvProfileObjects 3 }

		
		-- 1.3.6.1.4.1.34592.1.5.1.1.1.4.3.1
		gponSrvProfilePortNumEntry OBJECT-TYPE
			SYNTAX GponSrvProfilePortNumEntry
			MAX-ACCESS not-accessible
			STATUS current
			DESCRIPTION
				"Description."
			INDEX { gponSrvProfileId }
			::= { gponSrvProfilePortNumTable 1 }

		
		GponSrvProfilePortNumEntry ::=
			SEQUENCE { 
				gponSrvProfileEthNum
					Integer32,
				gponSrvProfilePotsNum
					Integer32,
				gponSrvProfileCatvNum
					Integer32
			 }

		-- 1.3.6.1.4.1.34592.1.5.1.1.1.4.3.1.1
		gponSrvProfileEthNum OBJECT-TYPE
			SYNTAX Integer32 (0..8 | 65535)
			MAX-ACCESS read-write
			STATUS current
			DESCRIPTION
				"Description."
			::= { gponSrvProfilePortNumEntry 1 }

		
		-- 1.3.6.1.4.1.34592.1.5.1.1.1.4.3.1.2
		gponSrvProfilePotsNum OBJECT-TYPE
			SYNTAX Integer32 (0..8 | 65535)
			MAX-ACCESS read-write
			STATUS current
			DESCRIPTION
				"Description."
			::= { gponSrvProfilePortNumEntry 2 }

		
		-- 1.3.6.1.4.1.34592.1.5.1.1.1.4.3.1.3
		gponSrvProfileCatvNum OBJECT-TYPE
			SYNTAX Integer32 (0..8 | 65535)
			MAX-ACCESS read-write
			STATUS current
			DESCRIPTION
				"Description."
			::= { gponSrvProfilePortNumEntry 3 }

		
		-- 1.3.6.1.4.1.34592.1.5.1.1.1.4.4
		gponSrvProfileOntPortVlanCfgTable OBJECT-TYPE
			SYNTAX SEQUENCE OF GponSrvProfileOntPortVlanCfgEntry
			MAX-ACCESS not-accessible
			STATUS current
			DESCRIPTION
				"Description."
			::= { gponSrvProfileObjects 4 }

		
		-- 1.3.6.1.4.1.34592.1.5.1.1.1.4.4.1
		gponSrvProfileOntPortVlanCfgEntry OBJECT-TYPE
			SYNTAX GponSrvProfileOntPortVlanCfgEntry
			MAX-ACCESS not-accessible
			STATUS current
			DESCRIPTION
				"Description."
			INDEX { gponSrvProfileId, gponSrvProfileOntPortType, gponSrvProfileOntPortId, gponSrvProfileOntPortVlanEntryId }
			::= { gponSrvProfileOntPortVlanCfgTable 1 }

		
		GponSrvProfileOntPortVlanCfgEntry ::=
			SEQUENCE { 
				gponSrvProfileOntPortType
					INTEGER,
				gponSrvProfileOntPortId
					Integer32,
				gponSrvProfileOntPortVlanEntryId
					Integer32,
				gponSrvProfileOntPortVlanRowStatus
					RowStatus,
				gponSrvProfileOntPortVlanMode
					INTEGER,
				gponSrvProfileOntPortVlanSvlan
					Integer32,
				gponSrvProfileOntPortVlanSpri
					Integer32,
				gponSrvProfileOntPortCvlan
					GponVlanId,
				gponSrvProfileOntPortVlanCpri
					Integer32
			 }

		-- 1.3.6.1.4.1.34592.1.5.1.1.1.4.4.1.1
		gponSrvProfileOntPortType OBJECT-TYPE
			SYNTAX INTEGER { eth(1) }
			MAX-ACCESS not-accessible
			STATUS current
			DESCRIPTION
				"Description."
			::= { gponSrvProfileOntPortVlanCfgEntry 1 }

		
		-- 1.3.6.1.4.1.34592.1.5.1.1.1.4.4.1.2
		gponSrvProfileOntPortId OBJECT-TYPE
			SYNTAX Integer32 (1..8)
			MAX-ACCESS not-accessible
			STATUS current
			DESCRIPTION
				"Description."
			::= { gponSrvProfileOntPortVlanCfgEntry 2 }

		
		-- 1.3.6.1.4.1.34592.1.5.1.1.1.4.4.1.3
		gponSrvProfileOntPortVlanEntryId OBJECT-TYPE
			SYNTAX Integer32 (1..9)
			MAX-ACCESS not-accessible
			STATUS current
			DESCRIPTION
				"Description."
			::= { gponSrvProfileOntPortVlanCfgEntry 3 }

		
		-- 1.3.6.1.4.1.34592.1.5.1.1.1.4.4.1.4
		gponSrvProfileOntPortVlanRowStatus OBJECT-TYPE
			SYNTAX RowStatus
			MAX-ACCESS read-create
			STATUS current
			DESCRIPTION
				"Description."
			::= { gponSrvProfileOntPortVlanCfgEntry 4 }

		
		-- 1.3.6.1.4.1.34592.1.5.1.1.1.4.4.1.5
		gponSrvProfileOntPortVlanMode OBJECT-TYPE
			SYNTAX INTEGER
				{
				transparent(1),
				qinq(2),
				translation(3)
				}
			MAX-ACCESS read-create
			STATUS current
			DESCRIPTION
				"Description."
			::= { gponSrvProfileOntPortVlanCfgEntry 5 }

		
		-- 1.3.6.1.4.1.34592.1.5.1.1.1.4.4.1.6
		gponSrvProfileOntPortVlanSvlan OBJECT-TYPE
			SYNTAX Integer32 (1..4094)
			MAX-ACCESS read-create
			STATUS current
			DESCRIPTION
				"Description."
			::= { gponSrvProfileOntPortVlanCfgEntry 6 }

		
		-- 1.3.6.1.4.1.34592.1.5.1.1.1.4.4.1.7
		gponSrvProfileOntPortVlanSpri OBJECT-TYPE
			SYNTAX Integer32 (0..7 | 255)
			MAX-ACCESS read-create
			STATUS current
			DESCRIPTION
				"Description."
			::= { gponSrvProfileOntPortVlanCfgEntry 7 }

		
		-- 1.3.6.1.4.1.34592.1.5.1.1.1.4.4.1.8
		gponSrvProfileOntPortCvlan OBJECT-TYPE
			SYNTAX GponVlanId (1..4094)
			MAX-ACCESS read-create
			STATUS current
			DESCRIPTION
				"Description."
			::= { gponSrvProfileOntPortVlanCfgEntry 8 }

		
		-- 1.3.6.1.4.1.34592.1.5.1.1.1.4.4.1.9
		gponSrvProfileOntPortVlanCpri OBJECT-TYPE
			SYNTAX Integer32 (0..7 | 255)
			MAX-ACCESS read-create
			STATUS current
			DESCRIPTION
				"Description."
			::= { gponSrvProfileOntPortVlanCfgEntry 9 }

		
		-- 1.3.6.1.4.1.34592.1.5.1.1.1.4.5
		gponSrvProfileBindInfoTable OBJECT-TYPE
			SYNTAX SEQUENCE OF GponSrvProfileBindInfoEntry
			MAX-ACCESS not-accessible
			STATUS current
			DESCRIPTION
				"Description."
			::= { gponSrvProfileObjects 5 }

		
		-- 1.3.6.1.4.1.34592.1.5.1.1.1.4.5.1
		gponSrvProfileBindInfoEntry OBJECT-TYPE
			SYNTAX GponSrvProfileBindInfoEntry
			MAX-ACCESS not-accessible
			STATUS current
			DESCRIPTION
				"Description."
			INDEX { gponSrvProfileId, gponOltDeviceId, gponOltCardId, gponOltPortId }
			::= { gponSrvProfileBindInfoTable 1 }

		
		GponSrvProfileBindInfoEntry ::=
			SEQUENCE { 
				gponSrvProfileBindOnuList
					DisplayString
			 }

		-- 1.3.6.1.4.1.34592.1.5.1.1.1.4.5.1.2
		gponSrvProfileBindOnuList OBJECT-TYPE
			SYNTAX DisplayString
			MAX-ACCESS read-only
			STATUS current
			DESCRIPTION
				"Description."
			::= { gponSrvProfileBindInfoEntry 2 }

		
		-- 1.3.6.1.4.1.34592.1.5.1.1.1.6
		gponTrafficProfileObjects OBJECT IDENTIFIER ::= { gponProfileObjects 6 }

		
		-- 1.3.6.1.4.1.34592.1.5.1.1.1.6.1
		gponTrafficProfileInfoTable OBJECT-TYPE
			SYNTAX SEQUENCE OF GponTrafficProfileInfoEntry
			MAX-ACCESS not-accessible
			STATUS current
			DESCRIPTION
				"Description."
			::= { gponTrafficProfileObjects 1 }

		
		-- 1.3.6.1.4.1.34592.1.5.1.1.1.6.1.1
		gponTrafficProfileInfoEntry OBJECT-TYPE
			SYNTAX GponTrafficProfileInfoEntry
			MAX-ACCESS not-accessible
			STATUS current
			DESCRIPTION
				"Description."
			INDEX { gponTrafficProfileId }
			::= { gponTrafficProfileInfoTable 1 }

		
		GponTrafficProfileInfoEntry ::=
			SEQUENCE { 
				gponTrafficProfileId
					GponTrafficProfileId,
				gponTrafficProfileRowStatus
					RowStatus,
				gponTrafficProfileName
					GponTrafficProfileName,
				gponTrafficProfileBindNum
					Integer32
			 }

		-- 1.3.6.1.4.1.34592.1.5.1.1.1.6.1.1.1
		gponTrafficProfileId OBJECT-TYPE
			SYNTAX GponTrafficProfileId
			MAX-ACCESS read-write
			STATUS current
			DESCRIPTION
				"Description."
			::= { gponTrafficProfileInfoEntry 1 }

		
		-- 1.3.6.1.4.1.34592.1.5.1.1.1.6.1.1.2
		gponTrafficProfileRowStatus OBJECT-TYPE
			SYNTAX RowStatus
			MAX-ACCESS read-create
			STATUS current
			DESCRIPTION
				"Description."
			::= { gponTrafficProfileInfoEntry 2 }

		
		-- 1.3.6.1.4.1.34592.1.5.1.1.1.6.1.1.3
		gponTrafficProfileName OBJECT-TYPE
			SYNTAX GponTrafficProfileName
			MAX-ACCESS read-create
			STATUS current
			DESCRIPTION
				"Description."
			::= { gponTrafficProfileInfoEntry 3 }

		
		-- 1.3.6.1.4.1.34592.1.5.1.1.1.6.1.1.4
		gponTrafficProfileBindNum OBJECT-TYPE
			SYNTAX Integer32
			MAX-ACCESS read-only
			STATUS current
			DESCRIPTION
				"Description."
			::= { gponTrafficProfileInfoEntry 4 }

		
		-- 1.3.6.1.4.1.34592.1.5.1.1.1.6.3
		gponTrafficProfileCfgTable OBJECT-TYPE
			SYNTAX SEQUENCE OF GponTrafficProfileCfgEntry
			MAX-ACCESS not-accessible
			STATUS current
			DESCRIPTION
				"Description."
			::= { gponTrafficProfileObjects 3 }

		
		-- 1.3.6.1.4.1.34592.1.5.1.1.1.6.3.1
		gponTrafficProfileCfgEntry OBJECT-TYPE
			SYNTAX GponTrafficProfileCfgEntry
			MAX-ACCESS not-accessible
			STATUS current
			DESCRIPTION
				"Description."
			INDEX { gponTrafficProfileId }
			::= { gponTrafficProfileCfgTable 1 }

		
		GponTrafficProfileCfgEntry ::=
			SEQUENCE { 
				gponTrafficProfileCfgCir
					Integer32,
				gponTrafficProfileCfgPir
					Integer32,
				gponTrafficProfileCfgCbs
					Integer32,
				gponTrafficProfileCfgPbs
					Integer32,
				gponTrafficProfileCfgPriority
					Integer32
			 }

		-- 1.3.6.1.4.1.34592.1.5.1.1.1.6.3.1.1
		gponTrafficProfileCfgCir OBJECT-TYPE
			SYNTAX Integer32 (64..10240000)
			MAX-ACCESS read-write
			STATUS current
			DESCRIPTION
				"Description."
			::= { gponTrafficProfileCfgEntry 1 }

		
		-- 1.3.6.1.4.1.34592.1.5.1.1.1.6.3.1.2
		gponTrafficProfileCfgPir OBJECT-TYPE
			SYNTAX Integer32 (64..10240000)
			MAX-ACCESS read-write
			STATUS current
			DESCRIPTION
				"Description."
			::= { gponTrafficProfileCfgEntry 2 }

		
		-- 1.3.6.1.4.1.34592.1.5.1.1.1.6.3.1.3
		gponTrafficProfileCfgCbs OBJECT-TYPE
			SYNTAX Integer32 (2000..10240000)
			MAX-ACCESS read-write
			STATUS current
			DESCRIPTION
				"Description."
			::= { gponTrafficProfileCfgEntry 3 }

		
		-- 1.3.6.1.4.1.34592.1.5.1.1.1.6.3.1.4
		gponTrafficProfileCfgPbs OBJECT-TYPE
			SYNTAX Integer32 (2000..10240000)
			MAX-ACCESS read-write
			STATUS current
			DESCRIPTION
				"Description."
			::= { gponTrafficProfileCfgEntry 4 }

		
		-- 1.3.6.1.4.1.34592.1.5.1.1.1.6.3.1.5
		gponTrafficProfileCfgPriority OBJECT-TYPE
			SYNTAX Integer32 (0..7)
			MAX-ACCESS read-write
			STATUS current
			DESCRIPTION
				"Description."
			::= { gponTrafficProfileCfgEntry 5 }

		
		-- 1.3.6.1.4.1.34592.1.5.1.1.1.8
		gponSipAgentProfileObjects OBJECT IDENTIFIER ::= { gponProfileObjects 8 }

		
		-- 1.3.6.1.4.1.34592.1.5.1.1.1.8.1
		gponSipAgentProfileInfoTable OBJECT-TYPE
			SYNTAX SEQUENCE OF GponSipAgentProfileInfoEntry
			MAX-ACCESS not-accessible
			STATUS current
			DESCRIPTION
				"Description."
			::= { gponSipAgentProfileObjects 1 }

		
		-- 1.3.6.1.4.1.34592.1.5.1.1.1.8.1.1
		gponSipAgentProfileInfoEntry OBJECT-TYPE
			SYNTAX GponSipAgentProfileInfoEntry
			MAX-ACCESS not-accessible
			STATUS current
			DESCRIPTION
				"Description."
			INDEX { gponSipAgentProfileId }
			::= { gponSipAgentProfileInfoTable 1 }

		
		GponSipAgentProfileInfoEntry ::=
			SEQUENCE { 
				gponSipAgentProfileId
					GponSipAgentProfileId,
				gponSipAgentProfileRowStatus
					RowStatus,
				gponSipAgentProfileName
					GponSipAgentProfileName,
				gponSipAgentProfileBindNum
					Integer32
			 }

		-- 1.3.6.1.4.1.34592.1.5.1.1.1.8.1.1.1
		gponSipAgentProfileId OBJECT-TYPE
			SYNTAX GponSipAgentProfileId
			MAX-ACCESS not-accessible
			STATUS current
			DESCRIPTION
				"Description."
			::= { gponSipAgentProfileInfoEntry 1 }

		
		-- 1.3.6.1.4.1.34592.1.5.1.1.1.8.1.1.2
		gponSipAgentProfileRowStatus OBJECT-TYPE
			SYNTAX RowStatus
			MAX-ACCESS read-create
			STATUS current
			DESCRIPTION
				"Description."
			::= { gponSipAgentProfileInfoEntry 2 }

		
		-- 1.3.6.1.4.1.34592.1.5.1.1.1.8.1.1.3
		gponSipAgentProfileName OBJECT-TYPE
			SYNTAX GponSipAgentProfileName
			MAX-ACCESS read-create
			STATUS current
			DESCRIPTION
				"Description."
			::= { gponSipAgentProfileInfoEntry 3 }

		
		-- 1.3.6.1.4.1.34592.1.5.1.1.1.8.1.1.4
		gponSipAgentProfileBindNum OBJECT-TYPE
			SYNTAX Integer32
			MAX-ACCESS read-only
			STATUS current
			DESCRIPTION
				"Description."
			::= { gponSipAgentProfileInfoEntry 4 }

		
		-- 1.3.6.1.4.1.34592.1.5.1.1.1.8.2
		gponSipAgentProfileCfgTable OBJECT-TYPE
			SYNTAX SEQUENCE OF GponSipAgentProfileCfgEntry
			MAX-ACCESS not-accessible
			STATUS current
			DESCRIPTION
				"Description."
			::= { gponSipAgentProfileObjects 2 }

		
		-- 1.3.6.1.4.1.34592.1.5.1.1.1.8.2.1
		gponSipAgentProfileCfgEntry OBJECT-TYPE
			SYNTAX GponSipAgentProfileCfgEntry
			MAX-ACCESS not-accessible
			STATUS current
			DESCRIPTION
				"Description."
			INDEX { gponSipAgentProfileId }
			::= { gponSipAgentProfileCfgTable 1 }

		
		GponSipAgentProfileCfgEntry ::=
			SEQUENCE { 
				gponSipAgentProfileProxyServerUri
					GponSipUri,
				gponSipAgentProfileRtpDscp
					Integer32,
				gponSipAgentProfileRtpMinPort
					Integer32,
				gponSipAgentProfileRtpMaxPort
					Integer32,
				gponSipAgentProfileSignalDscp
					Integer32,
				gponSipAgentProfileSignalPort
					Integer32,
				gponSipAgentProfileSignalTransferMode
					INTEGER,
				gponSipAgentProfileRegistrationExpiration
					Unsigned32,
				gponSipAgentProfileRegistrationReregHeadStartTime
					Unsigned32,
				gponSipAgentProfileRegistrationServerUri
					GponSipUri,
				gponSipAgentProfileVoiceMailServerUri
					GponSipUri,
				gponSipAgentProfileVoiceMailSubscriptionExpiration
					Unsigned32,
				gponSipAgentProfileConfFactory
					GponSipUri,
				gponSipAgentProfileBridgedLineAgent
					GponSipUri,
				gponSipAgentProfileAuthRealm
					OCTET STRING,
				gponSipAgentProfileProxyServerPort
					Integer32,
				gponSipAgentProfileRegistrationServerPort
					Integer32,
				gponSipAgentProfileCfgOutboundServer
					GponSipUri,
				gponSipAgentProfileCfgOutboundServerPort
					Integer32
			 }

		-- 1.3.6.1.4.1.34592.1.5.1.1.1.8.2.1.1
		gponSipAgentProfileProxyServerUri OBJECT-TYPE
			SYNTAX GponSipUri
			MAX-ACCESS read-write
			STATUS current
			DESCRIPTION
				"Description."
			::= { gponSipAgentProfileCfgEntry 1 }

		
		-- 1.3.6.1.4.1.34592.1.5.1.1.1.8.2.1.2
		gponSipAgentProfileRtpDscp OBJECT-TYPE
			SYNTAX Integer32 (0..63)
			MAX-ACCESS read-write
			STATUS current
			DESCRIPTION
				"Description."
			::= { gponSipAgentProfileCfgEntry 2 }

		
		-- 1.3.6.1.4.1.34592.1.5.1.1.1.8.2.1.3
		gponSipAgentProfileRtpMinPort OBJECT-TYPE
			SYNTAX Integer32 (1..65535)
			MAX-ACCESS read-write
			STATUS current
			DESCRIPTION
				"Description."
			::= { gponSipAgentProfileCfgEntry 3 }

		
		-- 1.3.6.1.4.1.34592.1.5.1.1.1.8.2.1.4
		gponSipAgentProfileRtpMaxPort OBJECT-TYPE
			SYNTAX Integer32 (1..65535)
			MAX-ACCESS read-write
			STATUS current
			DESCRIPTION
				"Description."
			::= { gponSipAgentProfileCfgEntry 4 }

		
		-- 1.3.6.1.4.1.34592.1.5.1.1.1.8.2.1.5
		gponSipAgentProfileSignalDscp OBJECT-TYPE
			SYNTAX Integer32 (0..63)
			MAX-ACCESS read-write
			STATUS current
			DESCRIPTION
				"Description."
			::= { gponSipAgentProfileCfgEntry 5 }

		
		-- 1.3.6.1.4.1.34592.1.5.1.1.1.8.2.1.6
		gponSipAgentProfileSignalPort OBJECT-TYPE
			SYNTAX Integer32 (1..65535)
			MAX-ACCESS read-write
			STATUS current
			DESCRIPTION
				"Description."
			::= { gponSipAgentProfileCfgEntry 6 }

		
		-- 1.3.6.1.4.1.34592.1.5.1.1.1.8.2.1.7
		gponSipAgentProfileSignalTransferMode OBJECT-TYPE
			SYNTAX INTEGER
				{
				udp(0),
				tcp(1)
				}
			MAX-ACCESS read-write
			STATUS current
			DESCRIPTION
				"Description."
			::= { gponSipAgentProfileCfgEntry 7 }

		
		-- 1.3.6.1.4.1.34592.1.5.1.1.1.8.2.1.8
		gponSipAgentProfileRegistrationExpiration OBJECT-TYPE
			SYNTAX Unsigned32
			MAX-ACCESS read-write
			STATUS current
			DESCRIPTION
				"Description."
			::= { gponSipAgentProfileCfgEntry 8 }

		
		-- 1.3.6.1.4.1.34592.1.5.1.1.1.8.2.1.9
		gponSipAgentProfileRegistrationReregHeadStartTime OBJECT-TYPE
			SYNTAX Unsigned32
			MAX-ACCESS read-write
			STATUS current
			DESCRIPTION
				"Description."
			::= { gponSipAgentProfileCfgEntry 9 }

		
		-- 1.3.6.1.4.1.34592.1.5.1.1.1.8.2.1.10
		gponSipAgentProfileRegistrationServerUri OBJECT-TYPE
			SYNTAX GponSipUri
			MAX-ACCESS read-write
			STATUS current
			DESCRIPTION
				"Description."
			::= { gponSipAgentProfileCfgEntry 10 }

		
		-- 1.3.6.1.4.1.34592.1.5.1.1.1.8.2.1.11
		gponSipAgentProfileVoiceMailServerUri OBJECT-TYPE
			SYNTAX GponSipUri
			MAX-ACCESS read-write
			STATUS current
			DESCRIPTION
				"Description."
			::= { gponSipAgentProfileCfgEntry 11 }

		
		-- 1.3.6.1.4.1.34592.1.5.1.1.1.8.2.1.12
		gponSipAgentProfileVoiceMailSubscriptionExpiration OBJECT-TYPE
			SYNTAX Unsigned32
			MAX-ACCESS read-write
			STATUS current
			DESCRIPTION
				"Description."
			::= { gponSipAgentProfileCfgEntry 12 }

		
		-- 1.3.6.1.4.1.34592.1.5.1.1.1.8.2.1.13
		gponSipAgentProfileConfFactory OBJECT-TYPE
			SYNTAX GponSipUri
			MAX-ACCESS read-write
			STATUS current
			DESCRIPTION
				"Description."
			::= { gponSipAgentProfileCfgEntry 13 }

		
		-- 1.3.6.1.4.1.34592.1.5.1.1.1.8.2.1.14
		gponSipAgentProfileBridgedLineAgent OBJECT-TYPE
			SYNTAX GponSipUri
			MAX-ACCESS read-write
			STATUS current
			DESCRIPTION
				"Description."
			::= { gponSipAgentProfileCfgEntry 14 }

		
		-- 1.3.6.1.4.1.34592.1.5.1.1.1.8.2.1.15
		gponSipAgentProfileAuthRealm OBJECT-TYPE
			SYNTAX OCTET STRING (SIZE (1..24))
			MAX-ACCESS read-write
			STATUS current
			DESCRIPTION
				"Description."
			::= { gponSipAgentProfileCfgEntry 15 }

		
		-- 1.3.6.1.4.1.34592.1.5.1.1.1.8.2.1.16
		gponSipAgentProfileProxyServerPort OBJECT-TYPE
			SYNTAX Integer32 (0..65535)
			MAX-ACCESS read-write
			STATUS current
			DESCRIPTION
				"Description."
			::= { gponSipAgentProfileCfgEntry 16 }

		
		-- 1.3.6.1.4.1.34592.1.5.1.1.1.8.2.1.17
		gponSipAgentProfileRegistrationServerPort OBJECT-TYPE
			SYNTAX Integer32 (0..65535)
			MAX-ACCESS read-write
			STATUS current
			DESCRIPTION
				"Description."
			::= { gponSipAgentProfileCfgEntry 17 }

		
		-- 1.3.6.1.4.1.34592.1.5.1.1.1.8.2.1.18
		gponSipAgentProfileCfgOutboundServer OBJECT-TYPE
			SYNTAX GponSipUri
			MAX-ACCESS read-write
			STATUS current
			DESCRIPTION
				"Description."
			::= { gponSipAgentProfileCfgEntry 18 }

		
		-- 1.3.6.1.4.1.34592.1.5.1.1.1.8.2.1.19
		gponSipAgentProfileCfgOutboundServerPort OBJECT-TYPE
			SYNTAX Integer32 (0..65535)
			MAX-ACCESS read-write
			STATUS current
			DESCRIPTION
				"Description."
			::= { gponSipAgentProfileCfgEntry 19 }

		
		-- 1.3.6.1.4.1.34592.1.5.1.1.1.8.3
		gponSipAgentProfileBindInfoTable OBJECT-TYPE
			SYNTAX SEQUENCE OF GponSipAgentProfileBindInfoEntry
			MAX-ACCESS not-accessible
			STATUS current
			DESCRIPTION
				"Description."
			::= { gponSipAgentProfileObjects 3 }

		
		-- 1.3.6.1.4.1.34592.1.5.1.1.1.8.3.1
		gponSipAgentProfileBindInfoEntry OBJECT-TYPE
			SYNTAX GponSipAgentProfileBindInfoEntry
			MAX-ACCESS not-accessible
			STATUS current
			DESCRIPTION
				"Description."
			INDEX { gponSipAgentProfileId, gponSipAgentProfileBindInfoOnuId }
			::= { gponSipAgentProfileBindInfoTable 1 }

		
		GponSipAgentProfileBindInfoEntry ::=
			SEQUENCE { 
				gponSipAgentProfileBindInfoOnuId
					Integer32,
				gponSipAgentProfileBindPotsList
					DisplayString
			 }

		-- 1.3.6.1.4.1.34592.1.5.1.1.1.8.3.1.1
		gponSipAgentProfileBindInfoOnuId OBJECT-TYPE
			SYNTAX Integer32
			MAX-ACCESS not-accessible
			STATUS current
			DESCRIPTION
				"Description."
			::= { gponSipAgentProfileBindInfoEntry 1 }

		
		-- 1.3.6.1.4.1.34592.1.5.1.1.1.8.3.1.2
		gponSipAgentProfileBindPotsList OBJECT-TYPE
			SYNTAX DisplayString
			MAX-ACCESS read-only
			STATUS current
			DESCRIPTION
				"Description."
			::= { gponSipAgentProfileBindInfoEntry 2 }

		
		-- 1.3.6.1.4.1.34592.1.5.1.1.1.9
		gponSipRightFlagProfileObjects OBJECT IDENTIFIER ::= { gponProfileObjects 9 }

		
		-- 1.3.6.1.4.1.34592.1.5.1.1.1.9.1
		gponSipRightFlagProfileInfoTable OBJECT-TYPE
			SYNTAX SEQUENCE OF GponSipRightFlagProfileInfoEntry
			MAX-ACCESS not-accessible
			STATUS current
			DESCRIPTION
				"Description."
			::= { gponSipRightFlagProfileObjects 1 }

		
		-- 1.3.6.1.4.1.34592.1.5.1.1.1.9.1.1
		gponSipRightFlagProfileInfoEntry OBJECT-TYPE
			SYNTAX GponSipRightFlagProfileInfoEntry
			MAX-ACCESS not-accessible
			STATUS current
			DESCRIPTION
				"Description."
			INDEX { gponSipRightFlagProfileId }
			::= { gponSipRightFlagProfileInfoTable 1 }

		
		GponSipRightFlagProfileInfoEntry ::=
			SEQUENCE { 
				gponSipRightFlagProfileId
					GponSipRightFlagProfileId,
				gponSipRightFlagProfileRowStatus
					RowStatus,
				gponSipRightFlagProfileName
					GponSipRightFlagProfileName,
				gponSipRightFlagProfileBindNum
					Integer32
			 }

		-- 1.3.6.1.4.1.34592.1.5.1.1.1.9.1.1.1
		gponSipRightFlagProfileId OBJECT-TYPE
			SYNTAX GponSipRightFlagProfileId
			MAX-ACCESS not-accessible
			STATUS current
			DESCRIPTION
				"Description."
			::= { gponSipRightFlagProfileInfoEntry 1 }

		
		-- 1.3.6.1.4.1.34592.1.5.1.1.1.9.1.1.2
		gponSipRightFlagProfileRowStatus OBJECT-TYPE
			SYNTAX RowStatus
			MAX-ACCESS read-create
			STATUS current
			DESCRIPTION
				"Description."
			::= { gponSipRightFlagProfileInfoEntry 2 }

		
		-- 1.3.6.1.4.1.34592.1.5.1.1.1.9.1.1.3
		gponSipRightFlagProfileName OBJECT-TYPE
			SYNTAX GponSipRightFlagProfileName
			MAX-ACCESS read-create
			STATUS current
			DESCRIPTION
				"Description."
			::= { gponSipRightFlagProfileInfoEntry 3 }

		
		-- 1.3.6.1.4.1.34592.1.5.1.1.1.9.1.1.4
		gponSipRightFlagProfileBindNum OBJECT-TYPE
			SYNTAX Integer32
			MAX-ACCESS read-only
			STATUS current
			DESCRIPTION
				"Description."
			::= { gponSipRightFlagProfileInfoEntry 4 }

		
		-- 1.3.6.1.4.1.34592.1.5.1.1.1.9.2
		gponSipRightFlagProfileCfgTable OBJECT-TYPE
			SYNTAX SEQUENCE OF GponSipRightFlagProfileCfgEntry
			MAX-ACCESS not-accessible
			STATUS current
			DESCRIPTION
				"Description."
			::= { gponSipRightFlagProfileObjects 2 }

		
		-- 1.3.6.1.4.1.34592.1.5.1.1.1.9.2.1
		gponSipRightFlagProfileCfgEntry OBJECT-TYPE
			SYNTAX GponSipRightFlagProfileCfgEntry
			MAX-ACCESS not-accessible
			STATUS current
			DESCRIPTION
				"Description."
			INDEX { gponSipRightFlagProfileId }
			::= { gponSipRightFlagProfileCfgTable 1 }

		
		GponSipRightFlagProfileCfgEntry ::=
			SEQUENCE { 
				gponSipRightFlagProfileCallWaiting
					GponSwitch,
				gponSipRightFlagProfileCallProcess
					BITS,
				gponSipRightFlagProfileCallPresentation
					GponSwitch,
				gponSipRightFlagProfileHotline
					BITS,
				gponSipRightFlagProfileHotlineNum
					DisplayString
			 }

		-- 1.3.6.1.4.1.34592.1.5.1.1.1.9.2.1.1
		gponSipRightFlagProfileCallWaiting OBJECT-TYPE
			SYNTAX GponSwitch
			MAX-ACCESS read-write
			STATUS current
			DESCRIPTION
				"Description."
			::= { gponSipRightFlagProfileCfgEntry 1 }

		
		-- 1.3.6.1.4.1.34592.1.5.1.1.1.9.2.1.2
		gponSipRightFlagProfileCallProcess OBJECT-TYPE
			SYNTAX BITS
				{
				threeParty(0),
				callTransfer(1),
				callHold(2),
				callPark(3),
				doNotDisturb(4),
				conference(5)
				}
			MAX-ACCESS read-write
			STATUS current
			DESCRIPTION
				"Description."
			::= { gponSipRightFlagProfileCfgEntry 2 }

		
		-- 1.3.6.1.4.1.34592.1.5.1.1.1.9.2.1.3
		gponSipRightFlagProfileCallPresentation OBJECT-TYPE
			SYNTAX GponSwitch
			MAX-ACCESS read-write
			STATUS current
			DESCRIPTION
				"Description."
			::= { gponSipRightFlagProfileCfgEntry 3 }

		
		-- 1.3.6.1.4.1.34592.1.5.1.1.1.9.2.1.4
		gponSipRightFlagProfileHotline OBJECT-TYPE
			SYNTAX BITS
				{
				hotline(0),
				hotlineDelay(1)
				}
			MAX-ACCESS read-write
			STATUS current
			DESCRIPTION
				"Description."
			::= { gponSipRightFlagProfileCfgEntry 4 }

		
		-- 1.3.6.1.4.1.34592.1.5.1.1.1.9.2.1.5
		gponSipRightFlagProfileHotlineNum OBJECT-TYPE
			SYNTAX DisplayString (SIZE (1..31))
			MAX-ACCESS read-write
			STATUS current
			DESCRIPTION
				"Description."
			::= { gponSipRightFlagProfileCfgEntry 5 }

		
		-- 1.3.6.1.4.1.34592.1.5.1.1.1.9.4
		gponSipRightFlagProfileBindInfoTable OBJECT-TYPE
			SYNTAX SEQUENCE OF GponSipRightFlagProfileBindInfoEntry
			MAX-ACCESS not-accessible
			STATUS current
			DESCRIPTION
				"Description."
			::= { gponSipRightFlagProfileObjects 4 }

		
		-- 1.3.6.1.4.1.34592.1.5.1.1.1.9.4.1
		gponSipRightFlagProfileBindInfoEntry OBJECT-TYPE
			SYNTAX GponSipRightFlagProfileBindInfoEntry
			MAX-ACCESS not-accessible
			STATUS current
			DESCRIPTION
				"Description."
			INDEX { gponSipRightFlagProfileId, gponSipRightFlagProfileBindInfoOnuId }
			::= { gponSipRightFlagProfileBindInfoTable 1 }

		
		GponSipRightFlagProfileBindInfoEntry ::=
			SEQUENCE { 
				gponSipRightFlagProfileBindInfoOnuId
					Integer32,
				gponSipRightFlagProfileBindPotsList
					DisplayString
			 }

		-- 1.3.6.1.4.1.34592.1.5.1.1.1.9.4.1.1
		gponSipRightFlagProfileBindInfoOnuId OBJECT-TYPE
			SYNTAX Integer32
			MAX-ACCESS read-only
			STATUS current
			DESCRIPTION
				"Description."
			::= { gponSipRightFlagProfileBindInfoEntry 1 }

		
		-- 1.3.6.1.4.1.34592.1.5.1.1.1.9.4.1.2
		gponSipRightFlagProfileBindPotsList OBJECT-TYPE
			SYNTAX DisplayString
			MAX-ACCESS read-only
			STATUS current
			DESCRIPTION
				"Description."
			::= { gponSipRightFlagProfileBindInfoEntry 2 }

		
		-- 1.3.6.1.4.1.34592.1.5.1.1.1.10
		gponDigitMapProfileObjects OBJECT IDENTIFIER ::= { gponProfileObjects 10 }

		
		-- 1.3.6.1.4.1.34592.1.5.1.1.1.10.1
		gponDigitMapProfileInfoTable OBJECT-TYPE
			SYNTAX SEQUENCE OF GponDigitMapProfileInfoEntry
			MAX-ACCESS not-accessible
			STATUS current
			DESCRIPTION
				"Description."
			::= { gponDigitMapProfileObjects 1 }

		
		-- 1.3.6.1.4.1.34592.1.5.1.1.1.10.1.1
		gponDigitMapProfileInfoEntry OBJECT-TYPE
			SYNTAX GponDigitMapProfileInfoEntry
			MAX-ACCESS not-accessible
			STATUS current
			DESCRIPTION
				"Description."
			INDEX { gponDigitMapProfileId }
			::= { gponDigitMapProfileInfoTable 1 }

		
		GponDigitMapProfileInfoEntry ::=
			SEQUENCE { 
				gponDigitMapProfileId
					GponDigitMapProfileId,
				gponDigitMapProfileRowStatus
					RowStatus,
				gponDigitMapProfileName
					OCTET STRING,
				gponDigitMapProfileBindNum
					Integer32
			 }

		-- 1.3.6.1.4.1.34592.1.5.1.1.1.10.1.1.1
		gponDigitMapProfileId OBJECT-TYPE
			SYNTAX GponDigitMapProfileId
			MAX-ACCESS not-accessible
			STATUS current
			DESCRIPTION
				"Description."
			::= { gponDigitMapProfileInfoEntry 1 }

		
		-- 1.3.6.1.4.1.34592.1.5.1.1.1.10.1.1.2
		gponDigitMapProfileRowStatus OBJECT-TYPE
			SYNTAX RowStatus
			MAX-ACCESS read-create
			STATUS current
			DESCRIPTION
				"Description."
			::= { gponDigitMapProfileInfoEntry 2 }

		
		-- 1.3.6.1.4.1.34592.1.5.1.1.1.10.1.1.3
		gponDigitMapProfileName OBJECT-TYPE
			SYNTAX OCTET STRING (SIZE (1..32))
			MAX-ACCESS read-create
			STATUS current
			DESCRIPTION
				"Description."
			::= { gponDigitMapProfileInfoEntry 3 }

		
		-- 1.3.6.1.4.1.34592.1.5.1.1.1.10.1.1.4
		gponDigitMapProfileBindNum OBJECT-TYPE
			SYNTAX Integer32
			MAX-ACCESS read-only
			STATUS current
			DESCRIPTION
				"Description."
			::= { gponDigitMapProfileInfoEntry 4 }

		
		-- 1.3.6.1.4.1.34592.1.5.1.1.1.10.2
		gponDigitMapProfileCfgTable OBJECT-TYPE
			SYNTAX SEQUENCE OF GponDigitMapProfileCfgEntry
			MAX-ACCESS not-accessible
			STATUS current
			DESCRIPTION
				"Description."
			::= { gponDigitMapProfileObjects 2 }

		
		-- 1.3.6.1.4.1.34592.1.5.1.1.1.10.2.1
		gponDigitMapProfileCfgEntry OBJECT-TYPE
			SYNTAX GponDigitMapProfileCfgEntry
			MAX-ACCESS not-accessible
			STATUS current
			DESCRIPTION
				"Description."
			INDEX { gponDigitMapProfileId }
			::= { gponDigitMapProfileCfgTable 1 }

		
		GponDigitMapProfileCfgEntry ::=
			SEQUENCE { 
				gponDigitMapProfileCriticalDialTime
					Integer32,
				gponDigitMapProfileCfgPartialDialTime
					Integer32,
				gponDigitMapProfileCfgDigitmapFormat
					INTEGER
			 }

		-- 1.3.6.1.4.1.34592.1.5.1.1.1.10.2.1.1
		gponDigitMapProfileCriticalDialTime OBJECT-TYPE
			SYNTAX Integer32
			MAX-ACCESS read-write
			STATUS current
			DESCRIPTION
				"Description."
			::= { gponDigitMapProfileCfgEntry 1 }

		
		-- 1.3.6.1.4.1.34592.1.5.1.1.1.10.2.1.2
		gponDigitMapProfileCfgPartialDialTime OBJECT-TYPE
			SYNTAX Integer32
			MAX-ACCESS read-write
			STATUS current
			DESCRIPTION
				"Description."
			::= { gponDigitMapProfileCfgEntry 2 }

		
		-- 1.3.6.1.4.1.34592.1.5.1.1.1.10.2.1.3
		gponDigitMapProfileCfgDigitmapFormat OBJECT-TYPE
			SYNTAX INTEGER
				{
				notDefined(0),
				h248(1),
				ncs(2),
				vendorSpecific(3)
				}
			MAX-ACCESS read-write
			STATUS current
			DESCRIPTION
				"Description."
			::= { gponDigitMapProfileCfgEntry 3 }

		
		-- 1.3.6.1.4.1.34592.1.5.1.1.1.10.3
		gponDigitMapProfileDialPlanTable OBJECT-TYPE
			SYNTAX SEQUENCE OF GponDigitMapProfileDialPlanEntry
			MAX-ACCESS not-accessible
			STATUS current
			DESCRIPTION
				"Description."
			::= { gponDigitMapProfileObjects 3 }

		
		-- 1.3.6.1.4.1.34592.1.5.1.1.1.10.3.1
		gponDigitMapProfileDialPlanEntry OBJECT-TYPE
			SYNTAX GponDigitMapProfileDialPlanEntry
			MAX-ACCESS not-accessible
			STATUS current
			DESCRIPTION
				"Description."
			INDEX { gponDigitMapProfileId, gponDigitMapProfileDialPlanId }
			::= { gponDigitMapProfileDialPlanTable 1 }

		
		GponDigitMapProfileDialPlanEntry ::=
			SEQUENCE { 
				gponDigitMapProfileDialPlanId
					Integer32,
				gponDigitMapProfileDialPlanRowStatus
					RowStatus,
				gponDigitMapProfileDialPlanToken
					DisplayString
			 }

		-- 1.3.6.1.4.1.34592.1.5.1.1.1.10.3.1.1
		gponDigitMapProfileDialPlanId OBJECT-TYPE
			SYNTAX Integer32 (1..10)
			MAX-ACCESS not-accessible
			STATUS current
			DESCRIPTION
				"Description."
			::= { gponDigitMapProfileDialPlanEntry 1 }

		
		-- 1.3.6.1.4.1.34592.1.5.1.1.1.10.3.1.2
		gponDigitMapProfileDialPlanRowStatus OBJECT-TYPE
			SYNTAX RowStatus
			MAX-ACCESS read-create
			STATUS current
			DESCRIPTION
				"Description."
			::= { gponDigitMapProfileDialPlanEntry 2 }

		
		-- 1.3.6.1.4.1.34592.1.5.1.1.1.10.3.1.3
		gponDigitMapProfileDialPlanToken OBJECT-TYPE
			SYNTAX DisplayString (SIZE (1..27))
			MAX-ACCESS read-create
			STATUS current
			DESCRIPTION
				"Description."
			::= { gponDigitMapProfileDialPlanEntry 3 }

		
		-- 1.3.6.1.4.1.34592.1.5.1.1.1.10.4
		gponDigitMapProfileBindInfoTable OBJECT-TYPE
			SYNTAX SEQUENCE OF GponDigitMapProfileBindInfoEntry
			MAX-ACCESS not-accessible
			STATUS current
			DESCRIPTION
				"Description."
			::= { gponDigitMapProfileObjects 4 }

		
		-- 1.3.6.1.4.1.34592.1.5.1.1.1.10.4.1
		gponDigitMapProfileBindInfoEntry OBJECT-TYPE
			SYNTAX GponDigitMapProfileBindInfoEntry
			MAX-ACCESS not-accessible
			STATUS current
			DESCRIPTION
				"Description."
			INDEX { gponDigitMapProfileId, gponDigitMapProfileBindInfoOnuId }
			::= { gponDigitMapProfileBindInfoTable 1 }

		
		GponDigitMapProfileBindInfoEntry ::=
			SEQUENCE { 
				gponDigitMapProfileBindInfoOnuId
					Integer32,
				gponDigitMapProfileBindPotsList
					DisplayString
			 }

		-- 1.3.6.1.4.1.34592.1.5.1.1.1.10.4.1.1
		gponDigitMapProfileBindInfoOnuId OBJECT-TYPE
			SYNTAX Integer32
			MAX-ACCESS read-only
			STATUS current
			DESCRIPTION
				"Description."
			::= { gponDigitMapProfileBindInfoEntry 1 }

		
		-- 1.3.6.1.4.1.34592.1.5.1.1.1.10.4.1.2
		gponDigitMapProfileBindPotsList OBJECT-TYPE
			SYNTAX DisplayString
			MAX-ACCESS read-only
			STATUS current
			DESCRIPTION
				"Description."
			::= { gponDigitMapProfileBindInfoEntry 2 }

		
		-- 1.3.6.1.4.1.34592.1.5.1.1.1.11
		gponPotsProfileObjects OBJECT IDENTIFIER ::= { gponProfileObjects 11 }

		
		-- 1.3.6.1.4.1.34592.1.5.1.1.1.11.1
		gponPotsProfileInfoTable OBJECT-TYPE
			SYNTAX SEQUENCE OF GponPotsProfileInfoEntry
			MAX-ACCESS not-accessible
			STATUS current
			DESCRIPTION
				"Description."
			::= { gponPotsProfileObjects 1 }

		
		-- 1.3.6.1.4.1.34592.1.5.1.1.1.11.1.1
		gponPotsProfileInfoEntry OBJECT-TYPE
			SYNTAX GponPotsProfileInfoEntry
			MAX-ACCESS not-accessible
			STATUS current
			DESCRIPTION
				"Description."
			INDEX { gponPotsProfileId }
			::= { gponPotsProfileInfoTable 1 }

		
		GponPotsProfileInfoEntry ::=
			SEQUENCE { 
				gponPotsProfileId
					GponPotsProfileId,
				gponPotsProfileRowStatus
					RowStatus,
				gponPotsProfileName
					OCTET STRING,
				gponPotsProfileBindNum
					Integer32
			 }

		-- 1.3.6.1.4.1.34592.1.5.1.1.1.11.1.1.1
		gponPotsProfileId OBJECT-TYPE
			SYNTAX GponPotsProfileId
			MAX-ACCESS not-accessible
			STATUS current
			DESCRIPTION
				"Description."
			::= { gponPotsProfileInfoEntry 1 }

		
		-- 1.3.6.1.4.1.34592.1.5.1.1.1.11.1.1.2
		gponPotsProfileRowStatus OBJECT-TYPE
			SYNTAX RowStatus
			MAX-ACCESS read-create
			STATUS current
			DESCRIPTION
				"Description."
			::= { gponPotsProfileInfoEntry 2 }

		
		-- 1.3.6.1.4.1.34592.1.5.1.1.1.11.1.1.3
		gponPotsProfileName OBJECT-TYPE
			SYNTAX OCTET STRING (SIZE (1..32))
			MAX-ACCESS read-create
			STATUS current
			DESCRIPTION
				"Description."
			::= { gponPotsProfileInfoEntry 3 }

		
		-- 1.3.6.1.4.1.34592.1.5.1.1.1.11.1.1.4
		gponPotsProfileBindNum OBJECT-TYPE
			SYNTAX Integer32
			MAX-ACCESS read-only
			STATUS current
			DESCRIPTION
				"Description."
			::= { gponPotsProfileInfoEntry 4 }

		
		-- 1.3.6.1.4.1.34592.1.5.1.1.1.11.2
		gponPotsProfileCfgTable OBJECT-TYPE
			SYNTAX SEQUENCE OF GponPotsProfileCfgEntry
			MAX-ACCESS not-accessible
			STATUS current
			DESCRIPTION
				"Description."
			::= { gponPotsProfileObjects 2 }

		
		-- 1.3.6.1.4.1.34592.1.5.1.1.1.11.2.1
		gponPotsProfileCfgEntry OBJECT-TYPE
			SYNTAX GponPotsProfileCfgEntry
			MAX-ACCESS not-accessible
			STATUS current
			DESCRIPTION
				"Description."
			INDEX { gponPotsProfileId }
			::= { gponPotsProfileCfgTable 1 }

		
		GponPotsProfileCfgEntry ::=
			SEQUENCE { 
				gponPotsProfileImpedance
					INTEGER,
				gponPotsProfileSignallingCode
					INTEGER,
				gponPotsProfileRxGain
					INTEGER,
				gponPotsProfileTxGain
					INTEGER
			 }

		-- 1.3.6.1.4.1.34592.1.5.1.1.1.11.2.1.1
		gponPotsProfileImpedance OBJECT-TYPE
			SYNTAX INTEGER
				{
				imp600Ohms(0),
				imp900Ohms(1),
				imp150nf750Ohm270Ohm(2),
				imp115nf820Ohm220Ohm(3),
				imp230nf1050Ohm320Ohm(4)
				}
			MAX-ACCESS read-write
			STATUS current
			DESCRIPTION
				"Description."
			::= { gponPotsProfileCfgEntry 1 }

		
		-- 1.3.6.1.4.1.34592.1.5.1.1.1.11.2.1.2
		gponPotsProfileSignallingCode OBJECT-TYPE
			SYNTAX INTEGER
				{
				none(0),
				loopStart(1),
				groundStart(2),
				loopReverseBattery(3),
				coinFirst(4),
				dialToneFirst(5),
				multiParty(6)
				}
			MAX-ACCESS read-write
			STATUS current
			DESCRIPTION
				"Description."
			::= { gponPotsProfileCfgEntry 2 }

		
		-- 1.3.6.1.4.1.34592.1.5.1.1.1.11.2.1.3
		gponPotsProfileRxGain OBJECT-TYPE
			SYNTAX INTEGER
				{
				gainN12d0dB(0),
				gainN11d5dB(1),
				gainN11d0dB(2),
				gainN10d5dB(3),
				gainN10d0dB(4),
				gainN9d5dB(5),
				gainN9d0dB(6),
				gainN8d5dB(7),
				gainN8d0dB(8),
				gainN7d5dB(9),
				gainN7d0dB(10),
				gainN6d5dB(11),
				gainN6d0dB(12),
				gainN5d5dB(13),
				gainN5d0dB(14),
				gainN4d5dB(15),
				gainN4d0dB(16),
				gainN3d5dB(17),
				gainN3d0dB(18),
				gainN2d5dB(19),
				gainN2d0dB(20),
				gainN1d5dB(21),
				gainN1d0dB(22),
				gainN0d5dB(23),
				gain0dB(24),
				gainP0d5dB(25),
				gainP1d0dB(26),
				gainP1d5dB(27),
				gainP2d0dB(28),
				gainP2d5dB(29),
				gainP3d0dB(30),
				gainP3d5dB(31),
				gainP4d0dB(32),
				gainP4d5dB(33),
				gainP5d0dB(34),
				gainP5d5dB(35),
				gainP6d0dB(36)
				}
			MAX-ACCESS read-write
			STATUS current
			DESCRIPTION
				"Description."
			::= { gponPotsProfileCfgEntry 3 }

		
		-- 1.3.6.1.4.1.34592.1.5.1.1.1.11.2.1.4
		gponPotsProfileTxGain OBJECT-TYPE
			SYNTAX INTEGER
				{
				gainN12d0dB(0),
				gainN11d5dB(1),
				gainN11d0dB(2),
				gainN10d5dB(3),
				gainN10d0dB(4),
				gainN9d5dB(5),
				gainN9d0dB(6),
				gainN8d5dB(7),
				gainN8d0dB(8),
				gainN7d5dB(9),
				gainN7d0dB(10),
				gainN6d5dB(11),
				gainN6d0dB(12),
				gainN5d5dB(13),
				gainN5d0dB(14),
				gainN4d5dB(15),
				gainN4d0dB(16),
				gainN3d5dB(17),
				gainN3d0dB(18),
				gainN2d5dB(19),
				gainN2d0dB(20),
				gainN1d5dB(21),
				gainN1d0dB(22),
				gainN0d5dB(23),
				gain0dB(24),
				gainP0d5dB(25),
				gainP1d0dB(26),
				gainP1d5dB(27),
				gainP2d0dB(28),
				gainP2d5dB(29),
				gainP3d0dB(30),
				gainP3d5dB(31),
				gainP4d0dB(32),
				gainP4d5dB(33),
				gainP5d0dB(34),
				gainP5d5dB(35),
				gainP6d0dB(36)
				}
			MAX-ACCESS read-write
			STATUS current
			DESCRIPTION
				"Description."
			::= { gponPotsProfileCfgEntry 4 }

		
		-- 1.3.6.1.4.1.34592.1.5.1.1.1.11.3
		gponPotsProfileBindInfoTable OBJECT-TYPE
			SYNTAX SEQUENCE OF GponPotsProfileBindInfoEntry
			MAX-ACCESS not-accessible
			STATUS current
			DESCRIPTION
				"Description."
			::= { gponPotsProfileObjects 3 }

		
		-- 1.3.6.1.4.1.34592.1.5.1.1.1.11.3.1
		gponPotsProfileBindInfoEntry OBJECT-TYPE
			SYNTAX GponPotsProfileBindInfoEntry
			MAX-ACCESS not-accessible
			STATUS current
			DESCRIPTION
				"Description."
			INDEX { gponPotsProfileId, gponPotsProfileBindInfoOnuId }
			::= { gponPotsProfileBindInfoTable 1 }

		
		GponPotsProfileBindInfoEntry ::=
			SEQUENCE { 
				gponPotsProfileBindInfoOnuId
					Integer32,
				gponPotsProfileBindPotsList
					DisplayString
			 }

		-- 1.3.6.1.4.1.34592.1.5.1.1.1.11.3.1.1
		gponPotsProfileBindInfoOnuId OBJECT-TYPE
			SYNTAX Integer32
			MAX-ACCESS read-only
			STATUS current
			DESCRIPTION
				"Description."
			::= { gponPotsProfileBindInfoEntry 1 }

		
		-- 1.3.6.1.4.1.34592.1.5.1.1.1.11.3.1.2
		gponPotsProfileBindPotsList OBJECT-TYPE
			SYNTAX DisplayString
			MAX-ACCESS read-only
			STATUS current
			DESCRIPTION
				"Description."
			::= { gponPotsProfileBindInfoEntry 2 }

		
		-- 1.3.6.1.4.1.34592.1.5.1.1.1.12
		gponTr069ProfileObjects OBJECT IDENTIFIER ::= { gponProfileObjects 12 }

		
		-- 1.3.6.1.4.1.34592.1.5.1.1.1.12.1
		gponTr069ProfileInfoTable OBJECT-TYPE
			SYNTAX SEQUENCE OF GponTr069ProfileInfoEntry
			MAX-ACCESS not-accessible
			STATUS current
			DESCRIPTION
				"Description."
			::= { gponTr069ProfileObjects 1 }

		
		-- 1.3.6.1.4.1.34592.1.5.1.1.1.12.1.1
		gponTr069ProfileInfoEntry OBJECT-TYPE
			SYNTAX GponTr069ProfileInfoEntry
			MAX-ACCESS not-accessible
			STATUS current
			DESCRIPTION
				"Description."
			INDEX { IMPLIED gponTr069ProfileId }
			::= { gponTr069ProfileInfoTable 1 }

		
		GponTr069ProfileInfoEntry ::=
			SEQUENCE { 
				gponTr069ProfileId
					GponTr069ProfileId,
				gponTr069ProfileName
					OCTET STRING,
				gponTr069ProfileBindTimes
					Integer32,
				gponTr069ProfileInfoRowStatus
					RowStatus
			 }

		-- 1.3.6.1.4.1.34592.1.5.1.1.1.12.1.1.1
		gponTr069ProfileId OBJECT-TYPE
			SYNTAX GponTr069ProfileId
			MAX-ACCESS not-accessible
			STATUS current
			DESCRIPTION
				"Description."
			::= { gponTr069ProfileInfoEntry 1 }

		
		-- 1.3.6.1.4.1.34592.1.5.1.1.1.12.1.1.2
		gponTr069ProfileName OBJECT-TYPE
			SYNTAX OCTET STRING (SIZE (1..32))
			MAX-ACCESS read-create
			STATUS current
			DESCRIPTION
				"Description."
			::= { gponTr069ProfileInfoEntry 2 }

		
		-- 1.3.6.1.4.1.34592.1.5.1.1.1.12.1.1.3
		gponTr069ProfileBindTimes OBJECT-TYPE
			SYNTAX Integer32
			MAX-ACCESS read-only
			STATUS current
			DESCRIPTION
				"Description."
			::= { gponTr069ProfileInfoEntry 3 }

		
		-- 1.3.6.1.4.1.34592.1.5.1.1.1.12.1.1.4
		gponTr069ProfileInfoRowStatus OBJECT-TYPE
			SYNTAX RowStatus
			MAX-ACCESS read-create
			STATUS current
			DESCRIPTION
				"Description."
			::= { gponTr069ProfileInfoEntry 4 }

		
		-- 1.3.6.1.4.1.34592.1.5.1.1.1.12.2
		gponTr069ProfileCfgTable OBJECT-TYPE
			SYNTAX SEQUENCE OF GponTr069ProfileCfgEntry
			MAX-ACCESS not-accessible
			STATUS current
			DESCRIPTION
				"Description."
			::= { gponTr069ProfileObjects 2 }

		
		-- 1.3.6.1.4.1.34592.1.5.1.1.1.12.2.1
		gponTr069ProfileCfgEntry OBJECT-TYPE
			SYNTAX GponTr069ProfileCfgEntry
			MAX-ACCESS not-accessible
			STATUS current
			DESCRIPTION
				"Description."
			INDEX { gponTr069ProfileId }
			::= { gponTr069ProfileCfgTable 1 }

		
		GponTr069ProfileCfgEntry ::=
			SEQUENCE { 
				gponTr069ProfileCfgAcsPassword
					OCTET STRING,
				gponTr069ProfileCfgAcsPort
					Unsigned32,
				gponTr069ProfileCfgAcsUrl
					OCTET STRING,
				gponTr069ProfileCfgAcsUserName
					OCTET STRING,
				gponTr069ProfileCfgAuthRealm
					OCTET STRING,
				gponTr069ProfileCfgConnectRequestAuth
					INTEGER,
				gponTr069ProfileCfgCpePassword
					OCTET STRING,
				gponTr069ProfileCfgCpePort
					Unsigned32,
				gponTr069ProfileCfgCpeUserName
					OCTET STRING,
				gponTr069ProfileCfgCpePath
					OCTET STRING,
				gponTr069ProfileCfgInform
					INTEGER,
				gponTr069ProfileCfgInformInterval
					Unsigned32
			 }

		-- 1.3.6.1.4.1.34592.1.5.1.1.1.12.2.1.1
		gponTr069ProfileCfgAcsPassword OBJECT-TYPE
			SYNTAX OCTET STRING (SIZE (1..25))
			MAX-ACCESS read-write
			STATUS current
			DESCRIPTION
				"Description."
			::= { gponTr069ProfileCfgEntry 1 }

		
		-- 1.3.6.1.4.1.34592.1.5.1.1.1.12.2.1.2
		gponTr069ProfileCfgAcsPort OBJECT-TYPE
			SYNTAX Unsigned32 (0..65535)
			MAX-ACCESS read-write
			STATUS current
			DESCRIPTION
				"Description."
			::= { gponTr069ProfileCfgEntry 2 }

		
		-- 1.3.6.1.4.1.34592.1.5.1.1.1.12.2.1.3
		gponTr069ProfileCfgAcsUrl OBJECT-TYPE
			SYNTAX OCTET STRING (SIZE (1..63))
			MAX-ACCESS read-write
			STATUS current
			DESCRIPTION
				"Description."
			::= { gponTr069ProfileCfgEntry 3 }

		
		-- 1.3.6.1.4.1.34592.1.5.1.1.1.12.2.1.4
		gponTr069ProfileCfgAcsUserName OBJECT-TYPE
			SYNTAX OCTET STRING (SIZE (1..50))
			MAX-ACCESS read-write
			STATUS current
			DESCRIPTION
				"Description."
			::= { gponTr069ProfileCfgEntry 4 }

		
		-- 1.3.6.1.4.1.34592.1.5.1.1.1.12.2.1.5
		gponTr069ProfileCfgAuthRealm OBJECT-TYPE
			SYNTAX OCTET STRING (SIZE (1..24))
			MAX-ACCESS read-write
			STATUS current
			DESCRIPTION
				"Description."
			::= { gponTr069ProfileCfgEntry 5 }

		
		-- 1.3.6.1.4.1.34592.1.5.1.1.1.12.2.1.6
		gponTr069ProfileCfgConnectRequestAuth OBJECT-TYPE
			SYNTAX INTEGER
				{
				disable(0),
				enable(1)
				}
			MAX-ACCESS read-write
			STATUS current
			DESCRIPTION
				"Description."
			::= { gponTr069ProfileCfgEntry 6 }

		
		-- 1.3.6.1.4.1.34592.1.5.1.1.1.12.2.1.7
		gponTr069ProfileCfgCpePassword OBJECT-TYPE
			SYNTAX OCTET STRING (SIZE (1..25))
			MAX-ACCESS read-write
			STATUS current
			DESCRIPTION
				"Description."
			::= { gponTr069ProfileCfgEntry 7 }

		
		-- 1.3.6.1.4.1.34592.1.5.1.1.1.12.2.1.8
		gponTr069ProfileCfgCpePort OBJECT-TYPE
			SYNTAX Unsigned32 (0..65535)
			MAX-ACCESS read-write
			STATUS current
			DESCRIPTION
				"Description."
			::= { gponTr069ProfileCfgEntry 8 }

		
		-- 1.3.6.1.4.1.34592.1.5.1.1.1.12.2.1.9
		gponTr069ProfileCfgCpeUserName OBJECT-TYPE
			SYNTAX OCTET STRING (SIZE (1..50))
			MAX-ACCESS read-write
			STATUS current
			DESCRIPTION
				"Description."
			::= { gponTr069ProfileCfgEntry 9 }

		
		-- 1.3.6.1.4.1.34592.1.5.1.1.1.12.2.1.10
		gponTr069ProfileCfgCpePath OBJECT-TYPE
			SYNTAX OCTET STRING (SIZE (1..63))
			MAX-ACCESS read-only
			STATUS current
			DESCRIPTION
				"Description."
			::= { gponTr069ProfileCfgEntry 10 }

		
		-- 1.3.6.1.4.1.34592.1.5.1.1.1.12.2.1.11
		gponTr069ProfileCfgInform OBJECT-TYPE
			SYNTAX INTEGER
				{
				disable(0),
				enable(1)
				}
			MAX-ACCESS read-write
			STATUS current
			DESCRIPTION
				"Description."
			::= { gponTr069ProfileCfgEntry 11 }

		
		-- 1.3.6.1.4.1.34592.1.5.1.1.1.12.2.1.12
		gponTr069ProfileCfgInformInterval OBJECT-TYPE
			SYNTAX Unsigned32 (1..4294967295)
			MAX-ACCESS read-write
			STATUS current
			DESCRIPTION
				"Description."
			::= { gponTr069ProfileCfgEntry 12 }

		
		-- 1.3.6.1.4.1.34592.1.5.1.1.1.12.3
		gponTr069ProfileBindInfoTable OBJECT-TYPE
			SYNTAX SEQUENCE OF GponTr069ProfileBindInfoEntry
			MAX-ACCESS not-accessible
			STATUS current
			DESCRIPTION
				"Description."
			::= { gponTr069ProfileObjects 3 }

		
		-- 1.3.6.1.4.1.34592.1.5.1.1.1.12.3.1
		gponTr069ProfileBindInfoEntry OBJECT-TYPE
			SYNTAX GponTr069ProfileBindInfoEntry
			MAX-ACCESS not-accessible
			STATUS current
			DESCRIPTION
				"Description."
			INDEX { gponTr069ProfileId, gponOltDeviceId, gponOltCardId, gponOltPortId }
			::= { gponTr069ProfileBindInfoTable 1 }

		
		GponTr069ProfileBindInfoEntry ::=
			SEQUENCE { 
				gponTr069ProfileBindInfoOnuList
					DisplayString
			 }

		-- 1.3.6.1.4.1.34592.1.5.1.1.1.12.3.1.1
		gponTr069ProfileBindInfoOnuList OBJECT-TYPE
			SYNTAX DisplayString
			MAX-ACCESS read-only
			STATUS current
			DESCRIPTION
				"Description."
			::= { gponTr069ProfileBindInfoEntry 1 }

		
		-- 1.3.6.1.4.1.34592.1.5.1.1.1.13
		gponOpticalAlarmProfile OBJECT IDENTIFIER ::= { gponProfileObjects 13 }

		
		-- 1.3.6.1.4.1.34592.1.5.1.1.1.13.1
		gponOpticalAlarmProfileTable OBJECT-TYPE
			SYNTAX SEQUENCE OF GponOpticalAlarmProfileEntry
			MAX-ACCESS not-accessible
			STATUS current
			DESCRIPTION
				"该表单位为0.01.例如配置TX为10dbm，则需输入1000dbm."
			::= { gponOpticalAlarmProfile 1 }

		
		-- 1.3.6.1.4.1.34592.1.5.1.1.1.13.1.1
		gponOpticalAlarmProfileEntry OBJECT-TYPE
			SYNTAX GponOpticalAlarmProfileEntry
			MAX-ACCESS not-accessible
			STATUS current
			DESCRIPTION
				"单位0.01."
			INDEX { gponOpticalAlarmProfileId }
			::= { gponOpticalAlarmProfileTable 1 }

		
		GponOpticalAlarmProfileEntry ::=
			SEQUENCE { 
				gponOpticalAlarmProfileId
					Integer32,
				gponOpticalAlarmProfileName
					DisplayString,
				gponOpticalTxWarningUpperThreshold
					Integer32,
				gponOpticalTxWarningLowerThreshold
					Integer32,
				gponOpticalTxAlarmUpperThreshold
					Integer32,
				gponOpticalTxAlarmLowerThreshold
					Integer32,
				gponOpticalRxWarningUpperThreshold
					Integer32,
				gponOpticalRxWarningLowerThreshold
					Integer32,
				gponOpticalRxAlarmUpperThreshold
					Integer32,
				gponOpticalRxAlarmLowerThreshold
					Integer32,
				gponOpticalBiasWarningUpperThreshold
					Integer32,
				gponOpticalBiasWarningLowerThreshold
					Integer32,
				gponOpticalBiasAlarmUpperThreshold
					Integer32,
				gponOpticalBiasAlarmLowerThreshold
					Integer32,
				gponOpticalVccWarningUpperThreshold
					Integer32,
				gponOpticalVccWarningLowerThreshold
					Integer32,
				gponOpticalVccAlarmUpperThreshold
					Integer32,
				gponOpticalVccAlarmLowerThreshold
					Integer32,
				gponTemperatureWarningUpperThreshold
					Integer32,
				gponTemperatureWarningLowerThreshold
					Integer32,
				gponTemperatureAlarmUpperThreshold
					Integer32,
				gponTemperatureAlarmLowerThreshold
					Integer32,
				gponOpticalOntCatvAlarmUpperThreshold
					Integer32,
				gponOpticalOntCatvAlarmLowerThreshold
					Integer32,
				gponOpticalAlarmProfileRowStatus
					RowStatus
			 }

		-- 1.3.6.1.4.1.34592.1.5.1.1.1.13.1.1.1
		gponOpticalAlarmProfileId OBJECT-TYPE
			SYNTAX Integer32
			MAX-ACCESS not-accessible
			STATUS current
			DESCRIPTION
				"Description."
			::= { gponOpticalAlarmProfileEntry 1 }

		
		-- 1.3.6.1.4.1.34592.1.5.1.1.1.13.1.1.2
		gponOpticalAlarmProfileName OBJECT-TYPE
			SYNTAX DisplayString
			MAX-ACCESS read-write
			STATUS current
			DESCRIPTION
				"Description."
			::= { gponOpticalAlarmProfileEntry 2 }

		
		-- 1.3.6.1.4.1.34592.1.5.1.1.1.13.1.1.3
		gponOpticalTxWarningUpperThreshold OBJECT-TYPE
			SYNTAX Integer32
			MAX-ACCESS read-write
			STATUS current
			DESCRIPTION
				"单位0.01."
			::= { gponOpticalAlarmProfileEntry 3 }

		
		-- 1.3.6.1.4.1.34592.1.5.1.1.1.13.1.1.4
		gponOpticalTxWarningLowerThreshold OBJECT-TYPE
			SYNTAX Integer32
			MAX-ACCESS read-write
			STATUS current
			DESCRIPTION
				"单位0.01."
			::= { gponOpticalAlarmProfileEntry 4 }

		
		-- 1.3.6.1.4.1.34592.1.5.1.1.1.13.1.1.5
		gponOpticalTxAlarmUpperThreshold OBJECT-TYPE
			SYNTAX Integer32
			MAX-ACCESS read-write
			STATUS current
			DESCRIPTION
				"单位0.01."
			::= { gponOpticalAlarmProfileEntry 5 }

		
		-- 1.3.6.1.4.1.34592.1.5.1.1.1.13.1.1.6
		gponOpticalTxAlarmLowerThreshold OBJECT-TYPE
			SYNTAX Integer32
			MAX-ACCESS read-write
			STATUS current
			DESCRIPTION
				"单位0.01."
			::= { gponOpticalAlarmProfileEntry 6 }

		
		-- 1.3.6.1.4.1.34592.1.5.1.1.1.13.1.1.7
		gponOpticalRxWarningUpperThreshold OBJECT-TYPE
			SYNTAX Integer32
			MAX-ACCESS read-write
			STATUS current
			DESCRIPTION
				"单位0.01."
			::= { gponOpticalAlarmProfileEntry 7 }

		
		-- 1.3.6.1.4.1.34592.1.5.1.1.1.13.1.1.8
		gponOpticalRxWarningLowerThreshold OBJECT-TYPE
			SYNTAX Integer32
			MAX-ACCESS read-write
			STATUS current
			DESCRIPTION
				"单位0.01."
			::= { gponOpticalAlarmProfileEntry 8 }

		
		-- 1.3.6.1.4.1.34592.1.5.1.1.1.13.1.1.9
		gponOpticalRxAlarmUpperThreshold OBJECT-TYPE
			SYNTAX Integer32
			MAX-ACCESS read-write
			STATUS current
			DESCRIPTION
				"单位0.01."
			::= { gponOpticalAlarmProfileEntry 9 }

		
		-- 1.3.6.1.4.1.34592.1.5.1.1.1.13.1.1.10
		gponOpticalRxAlarmLowerThreshold OBJECT-TYPE
			SYNTAX Integer32
			MAX-ACCESS read-write
			STATUS current
			DESCRIPTION
				"单位0.01."
			::= { gponOpticalAlarmProfileEntry 10 }

		
		-- 1.3.6.1.4.1.34592.1.5.1.1.1.13.1.1.11
		gponOpticalBiasWarningUpperThreshold OBJECT-TYPE
			SYNTAX Integer32
			MAX-ACCESS read-write
			STATUS current
			DESCRIPTION
				"单位0.01."
			::= { gponOpticalAlarmProfileEntry 11 }

		
		-- 1.3.6.1.4.1.34592.1.5.1.1.1.13.1.1.12
		gponOpticalBiasWarningLowerThreshold OBJECT-TYPE
			SYNTAX Integer32
			MAX-ACCESS read-write
			STATUS current
			DESCRIPTION
				"单位0.01."
			::= { gponOpticalAlarmProfileEntry 12 }

		
		-- 1.3.6.1.4.1.34592.1.5.1.1.1.13.1.1.13
		gponOpticalBiasAlarmUpperThreshold OBJECT-TYPE
			SYNTAX Integer32
			MAX-ACCESS read-write
			STATUS current
			DESCRIPTION
				"单位0.01."
			::= { gponOpticalAlarmProfileEntry 13 }

		
		-- 1.3.6.1.4.1.34592.1.5.1.1.1.13.1.1.14
		gponOpticalBiasAlarmLowerThreshold OBJECT-TYPE
			SYNTAX Integer32
			MAX-ACCESS read-write
			STATUS current
			DESCRIPTION
				"单位0.01."
			::= { gponOpticalAlarmProfileEntry 14 }

		
		-- 1.3.6.1.4.1.34592.1.5.1.1.1.13.1.1.15
		gponOpticalVccWarningUpperThreshold OBJECT-TYPE
			SYNTAX Integer32
			MAX-ACCESS read-write
			STATUS current
			DESCRIPTION
				"单位0.01."
			::= { gponOpticalAlarmProfileEntry 15 }

		
		-- 1.3.6.1.4.1.34592.1.5.1.1.1.13.1.1.16
		gponOpticalVccWarningLowerThreshold OBJECT-TYPE
			SYNTAX Integer32
			MAX-ACCESS read-write
			STATUS current
			DESCRIPTION
				"单位0.01."
			::= { gponOpticalAlarmProfileEntry 16 }

		
		-- 1.3.6.1.4.1.34592.1.5.1.1.1.13.1.1.17
		gponOpticalVccAlarmUpperThreshold OBJECT-TYPE
			SYNTAX Integer32
			MAX-ACCESS read-write
			STATUS current
			DESCRIPTION
				"单位0.01."
			::= { gponOpticalAlarmProfileEntry 17 }

		
		-- 1.3.6.1.4.1.34592.1.5.1.1.1.13.1.1.18
		gponOpticalVccAlarmLowerThreshold OBJECT-TYPE
			SYNTAX Integer32
			MAX-ACCESS read-write
			STATUS current
			DESCRIPTION
				"单位0.01."
			::= { gponOpticalAlarmProfileEntry 18 }

		
		-- 1.3.6.1.4.1.34592.1.5.1.1.1.13.1.1.19
		gponTemperatureWarningUpperThreshold OBJECT-TYPE
			SYNTAX Integer32
			MAX-ACCESS read-write
			STATUS current
			DESCRIPTION
				"单位0.01."
			::= { gponOpticalAlarmProfileEntry 19 }

		
		-- 1.3.6.1.4.1.34592.1.5.1.1.1.13.1.1.20
		gponTemperatureWarningLowerThreshold OBJECT-TYPE
			SYNTAX Integer32
			MAX-ACCESS read-write
			STATUS current
			DESCRIPTION
				"单位0.01."
			::= { gponOpticalAlarmProfileEntry 20 }

		
		-- 1.3.6.1.4.1.34592.1.5.1.1.1.13.1.1.21
		gponTemperatureAlarmUpperThreshold OBJECT-TYPE
			SYNTAX Integer32
			MAX-ACCESS read-write
			STATUS current
			DESCRIPTION
				"单位0.01."
			::= { gponOpticalAlarmProfileEntry 21 }

		
		-- 1.3.6.1.4.1.34592.1.5.1.1.1.13.1.1.22
		gponTemperatureAlarmLowerThreshold OBJECT-TYPE
			SYNTAX Integer32
			MAX-ACCESS read-write
			STATUS current
			DESCRIPTION
				"单位0.01."
			::= { gponOpticalAlarmProfileEntry 22 }

		
		-- 1.3.6.1.4.1.34592.1.5.1.1.1.13.1.1.23
		gponOpticalOntCatvAlarmUpperThreshold OBJECT-TYPE
			SYNTAX Integer32
			MAX-ACCESS read-write
			STATUS current
			DESCRIPTION
				"单位0.01."
			::= { gponOpticalAlarmProfileEntry 23 }

		
		-- 1.3.6.1.4.1.34592.1.5.1.1.1.13.1.1.24
		gponOpticalOntCatvAlarmLowerThreshold OBJECT-TYPE
			SYNTAX Integer32
			MAX-ACCESS read-write
			STATUS current
			DESCRIPTION
				"单位0.01."
			::= { gponOpticalAlarmProfileEntry 24 }

		
		-- 1.3.6.1.4.1.34592.1.5.1.1.1.13.1.1.25
		gponOpticalAlarmProfileRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { gponOpticalAlarmProfileEntry 25 }

		
		-- 1.3.6.1.4.1.34592.1.5.1.1.1.14
		gponProfileCollectObject OBJECT IDENTIFIER ::= { gponProfileObjects 14 }

		
		-- 1.3.6.1.4.1.34592.1.5.1.1.1.14.1
		gponSrvProfileCollectTable OBJECT-TYPE
			SYNTAX SEQUENCE OF GponSrvProfileCollectEntry
			MAX-ACCESS not-accessible
			STATUS current
			DESCRIPTION
				"Description."
			::= { gponProfileCollectObject 1 }

		
		-- 1.3.6.1.4.1.34592.1.5.1.1.1.14.1.1
		gponSrvProfileCollectEntry OBJECT-TYPE
			SYNTAX GponSrvProfileCollectEntry
			MAX-ACCESS not-accessible
			STATUS current
			DESCRIPTION
				"Description."
			INDEX { gponSrvProfileCollectIndex }
			::= { gponSrvProfileCollectTable 1 }

		
		GponSrvProfileCollectEntry ::=
			SEQUENCE { 
				gponSrvProfileCollectIndex
					Integer32,
				gponSrvProfileCollectInfo
					OCTET STRING
			 }

		-- 1.3.6.1.4.1.34592.1.5.1.1.1.14.1.1.1
		gponSrvProfileCollectIndex OBJECT-TYPE
			SYNTAX Integer32
			MAX-ACCESS not-accessible
			STATUS current
			DESCRIPTION
				"Description."
			::= { gponSrvProfileCollectEntry 1 }

		
		-- 1.3.6.1.4.1.34592.1.5.1.1.1.14.1.1.2
		gponSrvProfileCollectInfo OBJECT-TYPE
			SYNTAX OCTET STRING
			MAX-ACCESS read-only
			STATUS current
			DESCRIPTION
				"Description."
			::= { gponSrvProfileCollectEntry 2 }

		
		-- 1.3.6.1.4.1.34592.1.5.1.1.1.14.2
		gponLineProfileCollectTable OBJECT-TYPE
			SYNTAX SEQUENCE OF GponLineProfileCollectEntry
			MAX-ACCESS not-accessible
			STATUS current
			DESCRIPTION
				"Description."
			::= { gponProfileCollectObject 2 }

		
		-- 1.3.6.1.4.1.34592.1.5.1.1.1.14.2.1
		gponLineProfileCollectEntry OBJECT-TYPE
			SYNTAX GponLineProfileCollectEntry
			MAX-ACCESS not-accessible
			STATUS current
			DESCRIPTION
				"Description."
			INDEX { gponLineProfileCollectIndex }
			::= { gponLineProfileCollectTable 1 }

		
		GponLineProfileCollectEntry ::=
			SEQUENCE { 
				gponLineProfileCollectIndex
					Integer32,
				gponLineProfileCollectInfo
					OCTET STRING
			 }

		-- 1.3.6.1.4.1.34592.1.5.1.1.1.14.2.1.1
		gponLineProfileCollectIndex OBJECT-TYPE
			SYNTAX Integer32
			MAX-ACCESS not-accessible
			STATUS current
			DESCRIPTION
				"Description."
			::= { gponLineProfileCollectEntry 1 }

		
		-- 1.3.6.1.4.1.34592.1.5.1.1.1.14.2.1.2
		gponLineProfileCollectInfo OBJECT-TYPE
			SYNTAX OCTET STRING
			MAX-ACCESS read-only
			STATUS current
			DESCRIPTION
				"Description."
			::= { gponLineProfileCollectEntry 2 }

		
		-- 1.3.6.1.4.1.34592.1.5.1.1.1.15
		gponIGMPProfileObject OBJECT IDENTIFIER ::= { gponProfileObjects 15 }

		
		-- 1.3.6.1.4.1.34592.1.5.1.1.1.15.1
		gponOnuIgmpProfileInfoTable OBJECT-TYPE
			SYNTAX SEQUENCE OF GponOnuIgmpProfileInfoEntry
			MAX-ACCESS not-accessible
			STATUS current
			DESCRIPTION
				"
				可控组播用户权限表
				参考G.988-201210:  9.3.27 Multicast operations profile、9.3.28 Multicast subscriber config info
				"
			::= { gponIGMPProfileObject 1 }

		
		-- 1.3.6.1.4.1.34592.1.5.1.1.1.15.1.1
		gponOnuIgmpProfileInfoEntry OBJECT-TYPE
			SYNTAX GponOnuIgmpProfileInfoEntry
			MAX-ACCESS not-accessible
			STATUS current
			DESCRIPTION
				" "
			INDEX { gponOnuIgmpProfileIndex }
			::= { gponOnuIgmpProfileInfoTable 1 }

		
		GponOnuIgmpProfileInfoEntry ::=
			SEQUENCE { 
				gponOnuIgmpProfileIndex
					INTEGER,
				gponOnuIgmpProfileBindNunber
					INTEGER
			 }

		-- 1.3.6.1.4.1.34592.1.5.1.1.1.15.1.1.1
		gponOnuIgmpProfileIndex OBJECT-TYPE
			SYNTAX INTEGER
			MAX-ACCESS not-accessible
			STATUS current
			DESCRIPTION
				"
				Profile绱㈠紩鍙?"
			::= { gponOnuIgmpProfileInfoEntry 1 }

		
		-- 1.3.6.1.4.1.34592.1.5.1.1.1.15.1.1.2
		gponOnuIgmpProfileBindNunber OBJECT-TYPE
			SYNTAX INTEGER
			MAX-ACCESS read-only
			STATUS current
			DESCRIPTION
				"
				Profile鍚嶇О
				"
			::= { gponOnuIgmpProfileInfoEntry 2 }

		
		-- 1.3.6.1.4.1.34592.1.5.1.1.2
		gponControlObjects OBJECT IDENTIFIER ::= { gponObjects 2 }

		
		-- 1.3.6.1.4.1.34592.1.5.1.1.2.17
		gponOltObjects OBJECT IDENTIFIER ::= { gponControlObjects 17 }

		
		-- 1.3.6.1.4.1.34592.1.5.1.1.2.17.1
		gponOltControlTable OBJECT-TYPE
			SYNTAX SEQUENCE OF GponOltControlEntry
			MAX-ACCESS not-accessible
			STATUS current
			DESCRIPTION
				"Description."
			::= { gponOltObjects 1 }

		
		-- 1.3.6.1.4.1.34592.1.5.1.1.2.17.1.1
		gponOltControlEntry OBJECT-TYPE
			SYNTAX GponOltControlEntry
			MAX-ACCESS not-accessible
			STATUS current
			DESCRIPTION
				"Description."
			INDEX { gponOltDeviceId, gponOltCardId, gponOltPortId }
			::= { gponOltControlTable 1 }

		
		GponOltControlEntry ::=
			SEQUENCE { 
				gponOltDeviceId
					GponDeviceId,
				gponOltCardId
					GponCardId,
				gponOltPortId
					GponOltPortId,
				gponOltPortAutoFindSwitch
					GponSwitch,
				gponOltPortSwitch
					GponSwitch,
				gponOltPortStatus
					INTEGER
			 }

		-- 1.3.6.1.4.1.34592.1.5.1.1.2.17.1.1.1
		gponOltDeviceId OBJECT-TYPE
			SYNTAX GponDeviceId
			MAX-ACCESS not-accessible
			STATUS current
			DESCRIPTION
				"Description."
			::= { gponOltControlEntry 1 }

		
		-- 1.3.6.1.4.1.34592.1.5.1.1.2.17.1.1.2
		gponOltCardId OBJECT-TYPE
			SYNTAX GponCardId
			MAX-ACCESS not-accessible
			STATUS current
			DESCRIPTION
				"Description."
			::= { gponOltControlEntry 2 }

		
		-- 1.3.6.1.4.1.34592.1.5.1.1.2.17.1.1.3
		gponOltPortId OBJECT-TYPE
			SYNTAX GponOltPortId
			MAX-ACCESS not-accessible
			STATUS current
			DESCRIPTION
				"Description."
			::= { gponOltControlEntry 3 }

		
		-- 1.3.6.1.4.1.34592.1.5.1.1.2.17.1.1.4
		gponOltPortAutoFindSwitch OBJECT-TYPE
			SYNTAX GponSwitch
			MAX-ACCESS read-write
			STATUS current
			DESCRIPTION
				"Description."
			::= { gponOltControlEntry 4 }

		
		-- 1.3.6.1.4.1.34592.1.5.1.1.2.17.1.1.5
		gponOltPortSwitch OBJECT-TYPE
			SYNTAX GponSwitch
			MAX-ACCESS read-write
			STATUS current
			DESCRIPTION
				"Description."
			::= { gponOltControlEntry 5 }

		
		-- 1.3.6.1.4.1.34592.1.5.1.1.2.17.1.1.6
		gponOltPortStatus OBJECT-TYPE
			SYNTAX INTEGER
				{
				up(1),
				down(2)
				}
			MAX-ACCESS read-only
			STATUS current
			DESCRIPTION
				"Description."
			::= { gponOltControlEntry 6 }

		
		-- 1.3.6.1.4.1.34592.1.5.1.1.2.17.2
		gponOltPortDdmInfoTable OBJECT-TYPE
			SYNTAX SEQUENCE OF GponOltPortDdmInfoEntry
			MAX-ACCESS not-accessible
			STATUS current
			DESCRIPTION
				"Description."
			::= { gponOltObjects 2 }

		
		-- 1.3.6.1.4.1.34592.1.5.1.1.2.17.2.1
		gponOltPortDdmInfoEntry OBJECT-TYPE
			SYNTAX GponOltPortDdmInfoEntry
			MAX-ACCESS not-accessible
			STATUS current
			DESCRIPTION
				"Description."
			INDEX { gponOltDeviceId, gponOltCardId, gponOltPortId }
			::= { gponOltPortDdmInfoTable 1 }

		
		GponOltPortDdmInfoEntry ::=
			SEQUENCE { 
				gponOltPortDdmTemperature
					OCTET STRING,
				gponOltPortDdmVoltage
					OCTET STRING,
				gponOltPortDdmTxBiasCurrent
					OCTET STRING,
				gponOltPortDdmTxPower
					OCTET STRING,
				gponOltPortDdmRxPower
					OCTET STRING
			 }

		-- 1.3.6.1.4.1.34592.1.5.1.1.2.17.2.1.1
		gponOltPortDdmTemperature OBJECT-TYPE
			SYNTAX OCTET STRING (SIZE (0..32))
			MAX-ACCESS read-only
			STATUS current
			DESCRIPTION
				"Description."
			::= { gponOltPortDdmInfoEntry 1 }

		
		-- 1.3.6.1.4.1.34592.1.5.1.1.2.17.2.1.2
		gponOltPortDdmVoltage OBJECT-TYPE
			SYNTAX OCTET STRING (SIZE (0..32))
			MAX-ACCESS read-only
			STATUS current
			DESCRIPTION
				"Description."
			::= { gponOltPortDdmInfoEntry 2 }

		
		-- 1.3.6.1.4.1.34592.1.5.1.1.2.17.2.1.3
		gponOltPortDdmTxBiasCurrent OBJECT-TYPE
			SYNTAX OCTET STRING (SIZE (0..32))
			MAX-ACCESS read-only
			STATUS current
			DESCRIPTION
				"Description."
			::= { gponOltPortDdmInfoEntry 3 }

		
		-- 1.3.6.1.4.1.34592.1.5.1.1.2.17.2.1.4
		gponOltPortDdmTxPower OBJECT-TYPE
			SYNTAX OCTET STRING (SIZE (0..32))
			MAX-ACCESS read-only
			STATUS current
			DESCRIPTION
				"Description."
			::= { gponOltPortDdmInfoEntry 4 }

		
		-- 1.3.6.1.4.1.34592.1.5.1.1.2.17.2.1.5
		gponOltPortDdmRxPower OBJECT-TYPE
			SYNTAX OCTET STRING (SIZE (0..32))
			MAX-ACCESS read-only
			STATUS current
			DESCRIPTION
				"Description."
			::= { gponOltPortDdmInfoEntry 5 }

		
		-- 1.3.6.1.4.1.34592.1.5.1.1.2.17.3
		gponOltTransceiverInfoTable OBJECT-TYPE
			SYNTAX SEQUENCE OF GponOltTransceiverInfoEntry
			MAX-ACCESS not-accessible
			STATUS current
			DESCRIPTION
				"Description."
			::= { gponOltObjects 3 }

		
		-- 1.3.6.1.4.1.34592.1.5.1.1.2.17.3.1
		gponOltTransceiverInfoEntry OBJECT-TYPE
			SYNTAX GponOltTransceiverInfoEntry
			MAX-ACCESS not-accessible
			STATUS current
			DESCRIPTION
				"Description."
			INDEX { gponOltDeviceId, gponOltCardId, gponOltPortId }
			::= { gponOltTransceiverInfoTable 1 }

		
		GponOltTransceiverInfoEntry ::=
			SEQUENCE { 
				gponOltTransceiverVendor
					DisplayString,
				gponOltTransceiverProductName
					DisplayString,
				gponOltTransceiverVersion
					DisplayString,
				gponOltTransceiverSerialNumber
					DisplayString
			 }

		-- 1.3.6.1.4.1.34592.1.5.1.1.2.17.3.1.1
		gponOltTransceiverVendor OBJECT-TYPE
			SYNTAX DisplayString
			MAX-ACCESS read-only
			STATUS current
			DESCRIPTION
				"Description."
			::= { gponOltTransceiverInfoEntry 1 }

		
		-- 1.3.6.1.4.1.34592.1.5.1.1.2.17.3.1.2
		gponOltTransceiverProductName OBJECT-TYPE
			SYNTAX DisplayString
			MAX-ACCESS read-only
			STATUS current
			DESCRIPTION
				"Description."
			::= { gponOltTransceiverInfoEntry 2 }

		
		-- 1.3.6.1.4.1.34592.1.5.1.1.2.17.3.1.3
		gponOltTransceiverVersion OBJECT-TYPE
			SYNTAX DisplayString
			MAX-ACCESS read-only
			STATUS current
			DESCRIPTION
				"Description."
			::= { gponOltTransceiverInfoEntry 3 }

		
		-- 1.3.6.1.4.1.34592.1.5.1.1.2.17.3.1.4
		gponOltTransceiverSerialNumber OBJECT-TYPE
			SYNTAX DisplayString
			MAX-ACCESS read-only
			STATUS current
			DESCRIPTION
				"Description."
			::= { gponOltTransceiverInfoEntry 4 }

		
		-- 1.3.6.1.4.1.34592.1.5.1.1.2.17.4
		gponOltAutoAuthTable OBJECT IDENTIFIER ::= { gponOltObjects 4 }

		
		-- 1.3.6.1.4.1.34592.1.5.1.1.2.17.4.1
		gponOltAutoAuthControlTable OBJECT-TYPE
			SYNTAX SEQUENCE OF GponOltAutoAuthControlEntry
			MAX-ACCESS not-accessible
			STATUS current
			DESCRIPTION
				"Description."
			::= { gponOltAutoAuthTable 1 }

		
		-- 1.3.6.1.4.1.34592.1.5.1.1.2.17.4.1.1
		gponOltAutoAuthControlEntry OBJECT-TYPE
			SYNTAX GponOltAutoAuthControlEntry
			MAX-ACCESS not-accessible
			STATUS current
			DESCRIPTION
				"Description."
			INDEX { gponOltDeviceId, gponOltCardId }
			::= { gponOltAutoAuthControlTable 1 }

		
		GponOltAutoAuthControlEntry ::=
			SEQUENCE { 
				gponOltAutoAuthMode
					INTEGER,
				gponOltAutoAuthSwitch
					GponSwitch,
				gponOltPortAutoAuthSwitchBitMap
					OCTET STRING,
				gponOltAutoAuthRuleNumber
					Integer32
			 }

		-- 1.3.6.1.4.1.34592.1.5.1.1.2.17.4.1.1.1
		gponOltAutoAuthMode OBJECT-TYPE
			SYNTAX INTEGER
				{
				all(1),
				equid-auth(2),
				vendor-auth(3),
				equid-swver-auth(4)
				}
			MAX-ACCESS read-write
			STATUS current
			DESCRIPTION
				"Description."
			::= { gponOltAutoAuthControlEntry 1 }

		
		-- 1.3.6.1.4.1.34592.1.5.1.1.2.17.4.1.1.2
		gponOltAutoAuthSwitch OBJECT-TYPE
			SYNTAX GponSwitch
			MAX-ACCESS read-write
			STATUS current
			DESCRIPTION
				"Description."
			::= { gponOltAutoAuthControlEntry 2 }

		
		-- 1.3.6.1.4.1.34592.1.5.1.1.2.17.4.1.1.3
		gponOltPortAutoAuthSwitchBitMap OBJECT-TYPE
			SYNTAX OCTET STRING (SIZE (1))
			MAX-ACCESS read-write
			STATUS current
			DESCRIPTION
				"Description."
			::= { gponOltAutoAuthControlEntry 3 }

		
		-- 1.3.6.1.4.1.34592.1.5.1.1.2.17.4.1.1.4
		gponOltAutoAuthRuleNumber OBJECT-TYPE
			SYNTAX Integer32 (1..20)
			MAX-ACCESS read-only
			STATUS current
			DESCRIPTION
				"Description."
			::= { gponOltAutoAuthControlEntry 4 }

		
		-- 1.3.6.1.4.1.34592.1.5.1.1.2.17.4.2
		gponOltAutoAuthRuleTable OBJECT-TYPE
			SYNTAX SEQUENCE OF GponOltAutoAuthRuleEntry
			MAX-ACCESS not-accessible
			STATUS current
			DESCRIPTION
				"Description."
			::= { gponOltAutoAuthTable 2 }

		
		-- 1.3.6.1.4.1.34592.1.5.1.1.2.17.4.2.1
		gponOltAutoAuthRuleEntry OBJECT-TYPE
			SYNTAX GponOltAutoAuthRuleEntry
			MAX-ACCESS not-accessible
			STATUS current
			DESCRIPTION
				"Description."
			INDEX { gponOltAutoAuthRuleId }
			::= { gponOltAutoAuthRuleTable 1 }

		
		GponOltAutoAuthRuleEntry ::=
			SEQUENCE { 
				gponOltAutoAuthRuleId
					GponOltAutoAuthRuleId,
				gponOltAutoAuthRuleRowStatus
					RowStatus,
				gponOltAutoAuthVendorId
					OCTET STRING,
				gponOltAutoAuthEquipmentID
					OCTET STRING,
				gponOltAutoAuthSoftwareVersion
					OCTET STRING,
				gponOltAutoAuthLineProfileId
					GponLinePorfileId,
				gponOltAutoAuthSrvProfileId
					GponSrvProfileId,
				gponOltAutoAuthOnuNumber
					Integer32
			 }

		-- 1.3.6.1.4.1.34592.1.5.1.1.2.17.4.2.1.2
		gponOltAutoAuthRuleId OBJECT-TYPE
			SYNTAX GponOltAutoAuthRuleId
			MAX-ACCESS not-accessible
			STATUS current
			DESCRIPTION
				"Description."
			::= { gponOltAutoAuthRuleEntry 2 }

		
		-- 1.3.6.1.4.1.34592.1.5.1.1.2.17.4.2.1.3
		gponOltAutoAuthRuleRowStatus OBJECT-TYPE
			SYNTAX RowStatus
			MAX-ACCESS read-create
			STATUS current
			DESCRIPTION
				"Description."
			::= { gponOltAutoAuthRuleEntry 3 }

		
		-- 1.3.6.1.4.1.34592.1.5.1.1.2.17.4.2.1.4
		gponOltAutoAuthVendorId OBJECT-TYPE
			SYNTAX OCTET STRING (SIZE (4))
			MAX-ACCESS read-create
			STATUS current
			DESCRIPTION
				"Description."
			::= { gponOltAutoAuthRuleEntry 4 }

		
		-- 1.3.6.1.4.1.34592.1.5.1.1.2.17.4.2.1.5
		gponOltAutoAuthEquipmentID OBJECT-TYPE
			SYNTAX OCTET STRING (SIZE (1..20))
			MAX-ACCESS read-create
			STATUS current
			DESCRIPTION
				"Description."
			::= { gponOltAutoAuthRuleEntry 5 }

		
		-- 1.3.6.1.4.1.34592.1.5.1.1.2.17.4.2.1.6
		gponOltAutoAuthSoftwareVersion OBJECT-TYPE
			SYNTAX OCTET STRING (SIZE (1..14))
			MAX-ACCESS read-create
			STATUS current
			DESCRIPTION
				"Description."
			::= { gponOltAutoAuthRuleEntry 6 }

		
		-- 1.3.6.1.4.1.34592.1.5.1.1.2.17.4.2.1.7
		gponOltAutoAuthLineProfileId OBJECT-TYPE
			SYNTAX GponLinePorfileId
			MAX-ACCESS read-create
			STATUS current
			DESCRIPTION
				"Description."
			::= { gponOltAutoAuthRuleEntry 7 }

		
		-- 1.3.6.1.4.1.34592.1.5.1.1.2.17.4.2.1.8
		gponOltAutoAuthSrvProfileId OBJECT-TYPE
			SYNTAX GponSrvProfileId
			MAX-ACCESS read-create
			STATUS current
			DESCRIPTION
				"Description."
			::= { gponOltAutoAuthRuleEntry 8 }

		
		-- 1.3.6.1.4.1.34592.1.5.1.1.2.17.4.2.1.9
		gponOltAutoAuthOnuNumber OBJECT-TYPE
			SYNTAX Integer32
			MAX-ACCESS read-only
			STATUS current
			DESCRIPTION
				"Description."
			::= { gponOltAutoAuthRuleEntry 9 }

		
		-- 1.3.6.1.4.1.34592.1.5.1.1.2.17.5
		gponOltPortMacAddressTable OBJECT-TYPE
			SYNTAX SEQUENCE OF GponOltPortMacAddressEntry
			MAX-ACCESS not-accessible
			STATUS current
			DESCRIPTION
				"Description."
			::= { gponOltObjects 5 }

		
		-- 1.3.6.1.4.1.34592.1.5.1.1.2.17.5.1
		gponOltPortMacAddressEntry OBJECT-TYPE
			SYNTAX GponOltPortMacAddressEntry
			MAX-ACCESS not-accessible
			STATUS current
			DESCRIPTION
				"Description."
			INDEX { gponOltPortMacAddressPortId, gponOltPortMacAddressOnuId, gponOltPortMacAddressIndex }
			::= { gponOltPortMacAddressTable 1 }

		
		GponOltPortMacAddressEntry ::=
			SEQUENCE { 
				gponOltPortMacAddressIndex
					Integer32,
				gponOltPortMacAddress
					GponMac,
				gponOltPortMacAddressPortId
					Integer32,
				gponOltPortMacAddressOnuId
					Integer32,
				gponOltPortMacAddressGemPortId
					Integer32,
				gponOltPortMacAddressVlanId
					Integer32,
				gponOltPortMacAddressType
					INTEGER
			 }

		-- 1.3.6.1.4.1.34592.1.5.1.1.2.17.5.1.1
		gponOltPortMacAddressIndex OBJECT-TYPE
			SYNTAX Integer32
			MAX-ACCESS not-accessible
			STATUS current
			DESCRIPTION
				"Description."
			::= { gponOltPortMacAddressEntry 1 }

		
		-- 1.3.6.1.4.1.34592.1.5.1.1.2.17.5.1.2
		gponOltPortMacAddress OBJECT-TYPE
			SYNTAX GponMac
			MAX-ACCESS read-only
			STATUS current
			DESCRIPTION
				"Description."
			::= { gponOltPortMacAddressEntry 2 }

		
		-- 1.3.6.1.4.1.34592.1.5.1.1.2.17.5.1.3
		gponOltPortMacAddressPortId OBJECT-TYPE
			SYNTAX Integer32
			MAX-ACCESS not-accessible
			STATUS current
			DESCRIPTION
				"Description."
			::= { gponOltPortMacAddressEntry 3 }

		
		-- 1.3.6.1.4.1.34592.1.5.1.1.2.17.5.1.4
		gponOltPortMacAddressOnuId OBJECT-TYPE
			SYNTAX Integer32
			MAX-ACCESS not-accessible
			STATUS current
			DESCRIPTION
				"Description."
			::= { gponOltPortMacAddressEntry 4 }

		
		-- 1.3.6.1.4.1.34592.1.5.1.1.2.17.5.1.5
		gponOltPortMacAddressGemPortId OBJECT-TYPE
			SYNTAX Integer32
			MAX-ACCESS read-only
			STATUS current
			DESCRIPTION
				"Description."
			::= { gponOltPortMacAddressEntry 5 }

		
		-- 1.3.6.1.4.1.34592.1.5.1.1.2.17.5.1.6
		gponOltPortMacAddressVlanId OBJECT-TYPE
			SYNTAX Integer32
			MAX-ACCESS read-only
			STATUS current
			DESCRIPTION
				"Description."
			::= { gponOltPortMacAddressEntry 6 }

		
		-- 1.3.6.1.4.1.34592.1.5.1.1.2.17.5.1.7
		gponOltPortMacAddressType OBJECT-TYPE
			SYNTAX INTEGER
				{
				dynamic(0),
				static(1)
				}
			MAX-ACCESS read-only
			STATUS current
			DESCRIPTION
				"Description."
			::= { gponOltPortMacAddressEntry 7 }

			
		-- 1.3.6.1.4.1.34592.1.5.1.1.2.17.6
		gponOltStatisticsMacTable OBJECT-TYPE
			SYNTAX SEQUENCE OF GponOltStatisticsMacEntry
			MAX-ACCESS not-accessible
			STATUS current
			DESCRIPTION
				"Description."
			::= { gponOltObjects 6 }

		
		-- 1.3.6.1.4.1.34592.1.5.1.1.2.17.6.1
		gponOltStatisticsMacEntry OBJECT-TYPE
			SYNTAX GponOltStatisticsMacEntry
			MAX-ACCESS not-accessible
			STATUS current
			DESCRIPTION
				"Description."
			INDEX { gponOltDeviceId, gponOltCardId, gponOltPortId }
			::= { gponOltStatisticsMacTable 1 }

		
		GponOltStatisticsMacEntry ::=
			SEQUENCE { 
				oltMacUpFrames
					Counter64,
				oltMacUpBytes
					Counter64,
				oltMacUpFrames64
					Counter64,
				oltMacUpFrames127
					Counter64,
				oltMacUpFrames255
					Counter64,
				oltMacUpFrames511
					Counter64,
				oltMacUpFrames1023
					Counter64,
				oltMacUpFrames1518
					Counter64,
				oltMacUpFrames2047
					Counter64,
				oltMacUpFrames4095
					Counter64,
				oltMacUpFrames9216
					Counter64,
				oltMacUpFrames16383
					Counter64,
				oltMacUpGoodFrames
					Counter64,
				oltMacUpUnicastFrames
					Counter64,
				oltMacUpMulticastFrames
					Counter64,
				oltMacUpBroadCastFrames
					Counter64,
				oltMacUpPauseFrames
					Counter64,
				oltMacUpPfcFrames
					Counter64,
				oltMacUpJabberFrames
					Counter64,
				oltMacUpFcsErrors
					Counter64,
				oltMacUpControlFrames
					Counter64,
				oltMacUpOverSizeFrames
					Counter64,
				oltMacUpFragmentedFrames
					Counter64,
				oltMacUpErrorFrames
					Counter64,
				oltMacUpVlanFrames
					Counter64,
				oltMacUpDoubleVlanFrames
					Counter64,
				oltMacUpRuntFrames
					Counter64,
				oltMacUpUnderrunFrames
					Counter64,
				oltMacUpUnsupportedOpcode
					Counter64,
				oltMacUpUnsupportedDa
					Counter64,
				oltMacUpAlignmentErrors
					Counter64,
				oltMacUpLengthOutOfRange
					Counter64,
				oltMacUpCodeErrors
					Counter64,
				oltMacUpMtuCheckErrors
					Counter64,
				oltMacUpPromiscuousFrames
					Counter64,
				oltMacUpTruncatedFrames
					Counter64,
				oltMacUpUndersizeFrames
					Counter64,
				oltMacDownFrames
					Counter64,
				oltMacDownBytes
					Counter64,
				oltMacDownFrames64
					Counter64,
				oltMacDownFrames127
					Counter64,
				oltMacDownFrames255
					Counter64,
				oltMacDownFrames511
					Counter64,
				oltMacDownFrames1023
					Counter64,
				oltMacDownFrames1518
					Counter64,
				oltMacDownFrames2047
					Counter64,
				oltMacDownFrames4095
					Counter64,
				oltMacDownFrames9216
					Counter64,
				oltMacDownFrames16383
					Counter64,
				oltMacDownGoodFrames
					Counter64,
				oltMacDownUnicastFrames
					Counter64,
				oltMacDownMulticastFrames
					Counter64,
				oltMacDownBroadCastFrames
					Counter64,
				oltMacDownPauseFrames
					Counter64,
				oltMacDownPfcFrames
					Counter64,
				oltMacDownJabberFrames
					Counter64,
				oltMacDownFcsErrors
					Counter64,
				oltMacDownControlFrames
					Counter64,
				oltMacDownOverSizeFrames
					Counter64,
				oltMacDownFragmentedFrames
					Counter64,
				oltMacDownErrorFrames
					Counter64,
				oltMacDownVlanFrames
					Counter64,
				oltMacDownDoubleVlanFrames
					Counter64,
				oltMacDownRuntFrames
					Counter64,
				oltMacDownUnderrunFrames
					Counter64,
				oltMacDownUnsupportedOpcode
					Counter64,
				oltMacDownUnsupportedDa
					Counter64,
				oltMacDownAlignmentErrors
					Counter64,
				oltMacDownLengthOutOfRange
					Counter64,
				oltMacDownCodeErrors
					Counter64,
				oltMacDownMtuCheckErrors
					Counter64,
				oltMacDownPromiscuousFrames
					Counter64,
				oltMacDownTruncatedFrames
					Counter64,
				oltMacDownUndersizeFrames
					Counter64,
				oltMacResetFrames
					Integer32
			 }

		-- 1.3.6.1.4.1.34592.1.5.1.1.2.17.6.1.1
		oltMacUpFrames OBJECT-TYPE
			SYNTAX Counter64
			MAX-ACCESS read-only
			STATUS current
			DESCRIPTION
				"Description."
			::= { gponOltStatisticsMacEntry 1 }

		
		-- 1.3.6.1.4.1.34592.1.5.1.1.2.17.6.1.2
		oltMacUpBytes OBJECT-TYPE
			SYNTAX Counter64
			MAX-ACCESS read-only
			STATUS current
			DESCRIPTION
				"Description."
			::= { gponOltStatisticsMacEntry 2 }

		
		-- 1.3.6.1.4.1.34592.1.5.1.1.2.17.6.1.3
		oltMacUpFrames64 OBJECT-TYPE
			SYNTAX Counter64
			MAX-ACCESS read-only
			STATUS current
			DESCRIPTION
				"Description."
			::= { gponOltStatisticsMacEntry 3 }

		
		-- 1.3.6.1.4.1.34592.1.5.1.1.2.17.6.1.4
		oltMacUpFrames127 OBJECT-TYPE
			SYNTAX Counter64
			MAX-ACCESS read-only
			STATUS current
			DESCRIPTION
				"Description."
			::= { gponOltStatisticsMacEntry 4 }

		
		-- 1.3.6.1.4.1.34592.1.5.1.1.2.17.6.1.5
		oltMacUpFrames255 OBJECT-TYPE
			SYNTAX Counter64
			MAX-ACCESS read-only
			STATUS current
			DESCRIPTION
				"Description."
			::= { gponOltStatisticsMacEntry 5 }

		
		-- 1.3.6.1.4.1.34592.1.5.1.1.2.17.6.1.6
		oltMacUpFrames511 OBJECT-TYPE
			SYNTAX Counter64
			MAX-ACCESS read-only
			STATUS current
			DESCRIPTION
				"Description."
			::= { gponOltStatisticsMacEntry 6 }

		
		-- 1.3.6.1.4.1.34592.1.5.1.1.2.17.6.1.7
		oltMacUpFrames1023 OBJECT-TYPE
			SYNTAX Counter64
			MAX-ACCESS read-only
			STATUS current
			DESCRIPTION
				"Description."
			::= { gponOltStatisticsMacEntry 7 }

		
		-- 1.3.6.1.4.1.34592.1.5.1.1.2.17.6.1.8
		oltMacUpFrames1518 OBJECT-TYPE
			SYNTAX Counter64
			MAX-ACCESS read-only
			STATUS current
			DESCRIPTION
				"Description."
			::= { gponOltStatisticsMacEntry 8 }

		
		-- 1.3.6.1.4.1.34592.1.5.1.1.2.17.6.1.9
		oltMacUpFrames2047 OBJECT-TYPE
			SYNTAX Counter64
			MAX-ACCESS read-only
			STATUS current
			DESCRIPTION
				"Description."
			::= { gponOltStatisticsMacEntry 9 }

		
		-- 1.3.6.1.4.1.34592.1.5.1.1.2.17.6.1.10
		oltMacUpFrames4095 OBJECT-TYPE
			SYNTAX Counter64
			MAX-ACCESS read-only
			STATUS current
			DESCRIPTION
				"Description."
			::= { gponOltStatisticsMacEntry 10 }

		
		-- 1.3.6.1.4.1.34592.1.5.1.1.2.17.6.1.11
		oltMacUpFrames9216 OBJECT-TYPE
			SYNTAX Counter64
			MAX-ACCESS read-only
			STATUS current
			DESCRIPTION
				"Description."
			::= { gponOltStatisticsMacEntry 11 }

		
		-- 1.3.6.1.4.1.34592.1.5.1.1.2.17.6.1.12
		oltMacUpFrames16383 OBJECT-TYPE
			SYNTAX Counter64
			MAX-ACCESS read-only
			STATUS current
			DESCRIPTION
				"Description."
			::= { gponOltStatisticsMacEntry 12 }

		
		-- 1.3.6.1.4.1.34592.1.5.1.1.2.17.6.1.13
		oltMacUpGoodFrames OBJECT-TYPE
			SYNTAX Counter64
			MAX-ACCESS read-only
			STATUS current
			DESCRIPTION
				"Description."
			::= { gponOltStatisticsMacEntry 13 }

		
		-- 1.3.6.1.4.1.34592.1.5.1.1.2.17.6.1.14
		oltMacUpUnicastFrames OBJECT-TYPE
			SYNTAX Counter64
			MAX-ACCESS read-only
			STATUS current
			DESCRIPTION
				"Description."
			::= { gponOltStatisticsMacEntry 14 }

		
		-- 1.3.6.1.4.1.34592.1.5.1.1.2.17.6.1.15
		oltMacUpMulticastFrames OBJECT-TYPE
			SYNTAX Counter64
			MAX-ACCESS read-only
			STATUS current
			DESCRIPTION
				"Description."
			::= { gponOltStatisticsMacEntry 15 }

		
		-- 1.3.6.1.4.1.34592.1.5.1.1.2.17.6.1.16
		oltMacUpBroadCastFrames OBJECT-TYPE
			SYNTAX Counter64
			MAX-ACCESS read-only
			STATUS current
			DESCRIPTION
				"Description."
			::= { gponOltStatisticsMacEntry 16 }

		
		-- 1.3.6.1.4.1.34592.1.5.1.1.2.17.6.1.17
		oltMacUpPauseFrames OBJECT-TYPE
			SYNTAX Counter64
			MAX-ACCESS read-only
			STATUS current
			DESCRIPTION
				"Description."
			::= { gponOltStatisticsMacEntry 17 }

		
		-- 1.3.6.1.4.1.34592.1.5.1.1.2.17.6.1.18
		oltMacUpPfcFrames OBJECT-TYPE
			SYNTAX Counter64
			MAX-ACCESS read-only
			STATUS current
			DESCRIPTION
				"Description."
			::= { gponOltStatisticsMacEntry 18 }

		
		-- 1.3.6.1.4.1.34592.1.5.1.1.2.17.6.1.19
		oltMacUpJabberFrames OBJECT-TYPE
			SYNTAX Counter64
			MAX-ACCESS read-only
			STATUS current
			DESCRIPTION
				"Description."
			::= { gponOltStatisticsMacEntry 19 }

		
		-- 1.3.6.1.4.1.34592.1.5.1.1.2.17.6.1.20
		oltMacUpFcsErrors OBJECT-TYPE
			SYNTAX Counter64
			MAX-ACCESS read-only
			STATUS current
			DESCRIPTION
				"Description."
			::= { gponOltStatisticsMacEntry 20 }

		
		-- 1.3.6.1.4.1.34592.1.5.1.1.2.17.6.1.21
		oltMacUpControlFrames OBJECT-TYPE
			SYNTAX Counter64
			MAX-ACCESS read-only
			STATUS current
			DESCRIPTION
				"Description."
			::= { gponOltStatisticsMacEntry 21 }

		
		-- 1.3.6.1.4.1.34592.1.5.1.1.2.17.6.1.22
		oltMacUpOverSizeFrames OBJECT-TYPE
			SYNTAX Counter64
			MAX-ACCESS read-only
			STATUS current
			DESCRIPTION
				"Description."
			::= { gponOltStatisticsMacEntry 22 }

		
		-- 1.3.6.1.4.1.34592.1.5.1.1.2.17.6.1.23
		oltMacUpFragmentedFrames OBJECT-TYPE
			SYNTAX Counter64
			MAX-ACCESS read-only
			STATUS current
			DESCRIPTION
				"Description."
			::= { gponOltStatisticsMacEntry 23 }

		
		-- 1.3.6.1.4.1.34592.1.5.1.1.2.17.6.1.24
		oltMacUpErrorFrames OBJECT-TYPE
			SYNTAX Counter64
			MAX-ACCESS read-only
			STATUS current
			DESCRIPTION
				"Description."
			::= { gponOltStatisticsMacEntry 24 }

		
		-- 1.3.6.1.4.1.34592.1.5.1.1.2.17.6.1.25
		oltMacUpVlanFrames OBJECT-TYPE
			SYNTAX Counter64
			MAX-ACCESS read-only
			STATUS current
			DESCRIPTION
				"Description."
			::= { gponOltStatisticsMacEntry 25 }

		
		-- 1.3.6.1.4.1.34592.1.5.1.1.2.17.6.1.26
		oltMacUpDoubleVlanFrames OBJECT-TYPE
			SYNTAX Counter64
			MAX-ACCESS read-only
			STATUS current
			DESCRIPTION
				"Description."
			::= { gponOltStatisticsMacEntry 26 }

		
		-- 1.3.6.1.4.1.34592.1.5.1.1.2.17.6.1.27
		oltMacUpRuntFrames OBJECT-TYPE
			SYNTAX Counter64
			MAX-ACCESS read-only
			STATUS current
			DESCRIPTION
				"Description."
			::= { gponOltStatisticsMacEntry 27 }

		
		-- 1.3.6.1.4.1.34592.1.5.1.1.2.17.6.1.28
		oltMacUpUnderrunFrames OBJECT-TYPE
			SYNTAX Counter64
			MAX-ACCESS read-only
			STATUS current
			DESCRIPTION
				"Description."
			::= { gponOltStatisticsMacEntry 28 }

		
		-- 1.3.6.1.4.1.34592.1.5.1.1.2.17.6.1.29
		oltMacUpUnsupportedOpcode OBJECT-TYPE
			SYNTAX Counter64
			MAX-ACCESS read-only
			STATUS current
			DESCRIPTION
				"Description."
			::= { gponOltStatisticsMacEntry 29 }

		
		-- 1.3.6.1.4.1.34592.1.5.1.1.2.17.6.1.30
		oltMacUpUnsupportedDa OBJECT-TYPE
			SYNTAX Counter64
			MAX-ACCESS read-only
			STATUS current
			DESCRIPTION
				"Description."
			::= { gponOltStatisticsMacEntry 30 }

		
		-- 1.3.6.1.4.1.34592.1.5.1.1.2.17.6.1.31
		oltMacUpAlignmentErrors OBJECT-TYPE
			SYNTAX Counter64
			MAX-ACCESS read-only
			STATUS current
			DESCRIPTION
				"Description."
			::= { gponOltStatisticsMacEntry 31 }

		
		-- 1.3.6.1.4.1.34592.1.5.1.1.2.17.6.1.32
		oltMacUpLengthOutOfRange OBJECT-TYPE
			SYNTAX Counter64
			MAX-ACCESS read-only
			STATUS current
			DESCRIPTION
				"Description."
			::= { gponOltStatisticsMacEntry 32 }

		
		-- 1.3.6.1.4.1.34592.1.5.1.1.2.17.6.1.33
		oltMacUpCodeErrors OBJECT-TYPE
			SYNTAX Counter64
			MAX-ACCESS read-only
			STATUS current
			DESCRIPTION
				"Description."
			::= { gponOltStatisticsMacEntry 33 }

		
		-- 1.3.6.1.4.1.34592.1.5.1.1.2.17.6.1.34
		oltMacUpMtuCheckErrors OBJECT-TYPE
			SYNTAX Counter64
			MAX-ACCESS read-only
			STATUS current
			DESCRIPTION
				"Description."
			::= { gponOltStatisticsMacEntry 34 }

		
		-- 1.3.6.1.4.1.34592.1.5.1.1.2.17.6.1.35
		oltMacUpPromiscuousFrames OBJECT-TYPE
			SYNTAX Counter64
			MAX-ACCESS read-only
			STATUS current
			DESCRIPTION
				"Description."
			::= { gponOltStatisticsMacEntry 35 }

		
		-- 1.3.6.1.4.1.34592.1.5.1.1.2.17.6.1.36
		oltMacUpTruncatedFrames OBJECT-TYPE
			SYNTAX Counter64
			MAX-ACCESS read-only
			STATUS current
			DESCRIPTION
				"Description."
			::= { gponOltStatisticsMacEntry 36 }

		
		-- 1.3.6.1.4.1.34592.1.5.1.1.2.17.6.1.37
		oltMacUpUndersizeFrames OBJECT-TYPE
			SYNTAX Counter64
			MAX-ACCESS read-only
			STATUS current
			DESCRIPTION
				"Description."
			::= { gponOltStatisticsMacEntry 37 }

		
		-- 1.3.6.1.4.1.34592.1.5.1.1.2.17.6.1.38
		oltMacDownFrames OBJECT-TYPE
			SYNTAX Counter64
			MAX-ACCESS read-only
			STATUS current
			DESCRIPTION
				"Description."
			::= { gponOltStatisticsMacEntry 38 }

		
		-- 1.3.6.1.4.1.34592.1.5.1.1.2.17.6.1.39
		oltMacDownBytes OBJECT-TYPE
			SYNTAX Counter64
			MAX-ACCESS read-only
			STATUS current
			DESCRIPTION
				"Description."
			::= { gponOltStatisticsMacEntry 39 }

		
		-- 1.3.6.1.4.1.34592.1.5.1.1.2.17.6.1.40
		oltMacDownFrames64 OBJECT-TYPE
			SYNTAX Counter64
			MAX-ACCESS read-only
			STATUS current
			DESCRIPTION
				"Description."
			::= { gponOltStatisticsMacEntry 40 }

		
		-- 1.3.6.1.4.1.34592.1.5.1.1.2.17.6.1.41
		oltMacDownFrames127 OBJECT-TYPE
			SYNTAX Counter64
			MAX-ACCESS read-only
			STATUS current
			DESCRIPTION
				"Description."
			::= { gponOltStatisticsMacEntry 41 }

		
		-- 1.3.6.1.4.1.34592.1.5.1.1.2.17.6.1.42
		oltMacDownFrames255 OBJECT-TYPE
			SYNTAX Counter64
			MAX-ACCESS read-only
			STATUS current
			DESCRIPTION
				"Description."
			::= { gponOltStatisticsMacEntry 42 }

		
		-- 1.3.6.1.4.1.34592.1.5.1.1.2.17.6.1.43
		oltMacDownFrames511 OBJECT-TYPE
			SYNTAX Counter64
			MAX-ACCESS read-only
			STATUS current
			DESCRIPTION
				"Description."
			::= { gponOltStatisticsMacEntry 43 }

		
		-- 1.3.6.1.4.1.34592.1.5.1.1.2.17.6.1.44
		oltMacDownFrames1023 OBJECT-TYPE
			SYNTAX Counter64
			MAX-ACCESS read-only
			STATUS current
			DESCRIPTION
				"Description."
			::= { gponOltStatisticsMacEntry 44 }

		
		-- 1.3.6.1.4.1.34592.1.5.1.1.2.17.6.1.45
		oltMacDownFrames1518 OBJECT-TYPE
			SYNTAX Counter64
			MAX-ACCESS read-only
			STATUS current
			DESCRIPTION
				"Description."
			::= { gponOltStatisticsMacEntry 45 }

		
		-- 1.3.6.1.4.1.34592.1.5.1.1.2.17.6.1.46
		oltMacDownFrames2047 OBJECT-TYPE
			SYNTAX Counter64
			MAX-ACCESS read-only
			STATUS current
			DESCRIPTION
				"Description."
			::= { gponOltStatisticsMacEntry 46 }

		
		-- 1.3.6.1.4.1.34592.1.5.1.1.2.17.6.1.47
		oltMacDownFrames4095 OBJECT-TYPE
			SYNTAX Counter64
			MAX-ACCESS read-only
			STATUS current
			DESCRIPTION
				"Description."
			::= { gponOltStatisticsMacEntry 47 }

		
		-- 1.3.6.1.4.1.34592.1.5.1.1.2.17.6.1.48
		oltMacDownFrames9216 OBJECT-TYPE
			SYNTAX Counter64
			MAX-ACCESS read-only
			STATUS current
			DESCRIPTION
				"Description."
			::= { gponOltStatisticsMacEntry 48 }

		
		-- 1.3.6.1.4.1.34592.1.5.1.1.2.17.6.1.49
		oltMacDownFrames16383 OBJECT-TYPE
			SYNTAX Counter64
			MAX-ACCESS read-only
			STATUS current
			DESCRIPTION
				"Description."
			::= { gponOltStatisticsMacEntry 49 }

		
		-- 1.3.6.1.4.1.34592.1.5.1.1.2.17.6.1.50
		oltMacDownGoodFrames OBJECT-TYPE
			SYNTAX Counter64
			MAX-ACCESS read-only
			STATUS current
			DESCRIPTION
				"Description."
			::= { gponOltStatisticsMacEntry 50 }

		
		-- 1.3.6.1.4.1.34592.1.5.1.1.2.17.6.1.51
		oltMacDownUnicastFrames OBJECT-TYPE
			SYNTAX Counter64
			MAX-ACCESS read-only
			STATUS current
			DESCRIPTION
				"Description."
			::= { gponOltStatisticsMacEntry 51 }

		
		-- 1.3.6.1.4.1.34592.1.5.1.1.2.17.6.1.52
		oltMacDownMulticastFrames OBJECT-TYPE
			SYNTAX Counter64
			MAX-ACCESS read-only
			STATUS current
			DESCRIPTION
				"Description."
			::= { gponOltStatisticsMacEntry 52 }

		
		-- 1.3.6.1.4.1.34592.1.5.1.1.2.17.6.1.53
		oltMacDownBroadCastFrames OBJECT-TYPE
			SYNTAX Counter64
			MAX-ACCESS read-only
			STATUS current
			DESCRIPTION
				"Description."
			::= { gponOltStatisticsMacEntry 53 }

		
		-- 1.3.6.1.4.1.34592.1.5.1.1.2.17.6.1.54
		oltMacDownPauseFrames OBJECT-TYPE
			SYNTAX Counter64
			MAX-ACCESS read-only
			STATUS current
			DESCRIPTION
				"Description."
			::= { gponOltStatisticsMacEntry 54 }

		
		-- 1.3.6.1.4.1.34592.1.5.1.1.2.17.6.1.55
		oltMacDownPfcFrames OBJECT-TYPE
			SYNTAX Counter64
			MAX-ACCESS read-only
			STATUS current
			DESCRIPTION
				"Description."
			::= { gponOltStatisticsMacEntry 55 }

		
		-- 1.3.6.1.4.1.34592.1.5.1.1.2.17.6.1.56
		oltMacDownJabberFrames OBJECT-TYPE
			SYNTAX Counter64
			MAX-ACCESS read-only
			STATUS current
			DESCRIPTION
				"Description."
			::= { gponOltStatisticsMacEntry 56 }

		
		-- 1.3.6.1.4.1.34592.1.5.1.1.2.17.6.1.57
		oltMacDownFcsErrors OBJECT-TYPE
			SYNTAX Counter64
			MAX-ACCESS read-only
			STATUS current
			DESCRIPTION
				"Description."
			::= { gponOltStatisticsMacEntry 57 }

		
		-- 1.3.6.1.4.1.34592.1.5.1.1.2.17.6.1.58
		oltMacDownControlFrames OBJECT-TYPE
			SYNTAX Counter64
			MAX-ACCESS read-only
			STATUS current
			DESCRIPTION
				"Description."
			::= { gponOltStatisticsMacEntry 58 }

		
		-- 1.3.6.1.4.1.34592.1.5.1.1.2.17.6.1.59
		oltMacDownOverSizeFrames OBJECT-TYPE
			SYNTAX Counter64
			MAX-ACCESS read-only
			STATUS current
			DESCRIPTION
				"Description."
			::= { gponOltStatisticsMacEntry 59 }

		
		-- 1.3.6.1.4.1.34592.1.5.1.1.2.17.6.1.60
		oltMacDownFragmentedFrames OBJECT-TYPE
			SYNTAX Counter64
			MAX-ACCESS read-only
			STATUS current
			DESCRIPTION
				"Description."
			::= { gponOltStatisticsMacEntry 60 }

		
		-- 1.3.6.1.4.1.34592.1.5.1.1.2.17.6.1.61
		oltMacDownErrorFrames OBJECT-TYPE
			SYNTAX Counter64
			MAX-ACCESS read-only
			STATUS current
			DESCRIPTION
				"Description."
			::= { gponOltStatisticsMacEntry 61 }

		
		-- 1.3.6.1.4.1.34592.1.5.1.1.2.17.6.1.62
		oltMacDownVlanFrames OBJECT-TYPE
			SYNTAX Counter64
			MAX-ACCESS read-only
			STATUS current
			DESCRIPTION
				"Description."
			::= { gponOltStatisticsMacEntry 62 }

		
		-- 1.3.6.1.4.1.34592.1.5.1.1.2.17.6.1.63
		oltMacDownDoubleVlanFrames OBJECT-TYPE
			SYNTAX Counter64
			MAX-ACCESS read-only
			STATUS current
			DESCRIPTION
				"Description."
			::= { gponOltStatisticsMacEntry 63 }

		
		-- 1.3.6.1.4.1.34592.1.5.1.1.2.17.6.1.64
		oltMacDownRuntFrames OBJECT-TYPE
			SYNTAX Counter64
			MAX-ACCESS read-only
			STATUS current
			DESCRIPTION
				"Description."
			::= { gponOltStatisticsMacEntry 64 }

		
		-- 1.3.6.1.4.1.34592.1.5.1.1.2.17.6.1.65
		oltMacDownUnderrunFrames OBJECT-TYPE
			SYNTAX Counter64
			MAX-ACCESS read-only
			STATUS current
			DESCRIPTION
				"Description."
			::= { gponOltStatisticsMacEntry 65 }

		
		-- 1.3.6.1.4.1.34592.1.5.1.1.2.17.6.1.66
		oltMacDownUnsupportedOpcode OBJECT-TYPE
			SYNTAX Counter64
			MAX-ACCESS read-only
			STATUS current
			DESCRIPTION
				"Description."
			::= { gponOltStatisticsMacEntry 66 }

		
		-- 1.3.6.1.4.1.34592.1.5.1.1.2.17.6.1.67
		oltMacDownUnsupportedDa OBJECT-TYPE
			SYNTAX Counter64
			MAX-ACCESS read-only
			STATUS current
			DESCRIPTION
				"Description."
			::= { gponOltStatisticsMacEntry 67 }

		
		-- 1.3.6.1.4.1.34592.1.5.1.1.2.17.6.1.68
		oltMacDownAlignmentErrors OBJECT-TYPE
			SYNTAX Counter64
			MAX-ACCESS read-only
			STATUS current
			DESCRIPTION
				"Description."
			::= { gponOltStatisticsMacEntry 68 }

		
		-- 1.3.6.1.4.1.34592.1.5.1.1.2.17.6.1.69
		oltMacDownLengthOutOfRange OBJECT-TYPE
			SYNTAX Counter64
			MAX-ACCESS read-only
			STATUS current
			DESCRIPTION
				"Description."
			::= { gponOltStatisticsMacEntry 69 }

		
		-- 1.3.6.1.4.1.34592.1.5.1.1.2.17.6.1.70
		oltMacDownCodeErrors OBJECT-TYPE
			SYNTAX Counter64
			MAX-ACCESS read-only
			STATUS current
			DESCRIPTION
				"Description."
			::= { gponOltStatisticsMacEntry 70 }

		
		-- 1.3.6.1.4.1.34592.1.5.1.1.2.17.6.1.71
		oltMacDownMtuCheckErrors OBJECT-TYPE
			SYNTAX Counter64
			MAX-ACCESS read-only
			STATUS current
			DESCRIPTION
				"Description."
			::= { gponOltStatisticsMacEntry 71 }

		
		-- 1.3.6.1.4.1.34592.1.5.1.1.2.17.6.1.72
		oltMacDownPromiscuousFrames OBJECT-TYPE
			SYNTAX Counter64
			MAX-ACCESS read-only
			STATUS current
			DESCRIPTION
				"Description."
			::= { gponOltStatisticsMacEntry 72 }

		
		-- 1.3.6.1.4.1.34592.1.5.1.1.2.17.6.1.73
		oltMacDownTruncatedFrames OBJECT-TYPE
			SYNTAX Counter64
			MAX-ACCESS read-only
			STATUS current
			DESCRIPTION
				"Description."
			::= { gponOltStatisticsMacEntry 73 }

		
		-- 1.3.6.1.4.1.34592.1.5.1.1.2.17.6.1.74
		oltMacDownUndersizeFrames OBJECT-TYPE
			SYNTAX Counter64
			MAX-ACCESS read-only
			STATUS current
			DESCRIPTION
				"Description."
			::= { gponOltStatisticsMacEntry 74 }


		-- 1.3.6.1.4.1.34592.1.5.1.1.2.17.6.1.75
		oltMacResetFrames OBJECT-TYPE
			SYNTAX Integer32
			MAX-ACCESS read-write
			STATUS current
			DESCRIPTION
				"Description."
			::= { gponOltStatisticsMacEntry 75 }

		-- 1.3.6.1.4.1.34592.1.5.1.1.2.17.7
		gponOltGlobalConfigObjects OBJECT IDENTIFIER ::= { gponOltObjects 7 }

		
		-- 1.3.6.1.4.1.34592.1.5.1.1.2.17.7.1
		gponOltOnuWhiteTableSwitch OBJECT-TYPE
			SYNTAX INTEGER
				{
				disable(0),
				enable(1)
				}
			MAX-ACCESS read-write
			STATUS current
			DESCRIPTION
				"Description."
			::= { gponOltGlobalConfigObjects 1 }

		
		-- 1.3.6.1.4.1.34592.1.5.1.1.2.17.7.2
		gponOltOnuAutoFindTimeOut OBJECT-TYPE
			SYNTAX Integer32 (0 | 100..300)
			MAX-ACCESS read-write
			STATUS current
			DESCRIPTION
				"Description."
			::= { gponOltGlobalConfigObjects 2 }

		
		-- 1.3.6.1.4.1.34592.1.5.1.1.2.18
		gponOnuObjects OBJECT IDENTIFIER ::= { gponControlObjects 18 }

		
		-- 1.3.6.1.4.1.34592.1.5.1.1.2.18.1
		gponOnuConfigTable OBJECT-TYPE
			SYNTAX SEQUENCE OF GponOnuConfigEntry
			MAX-ACCESS not-accessible
			STATUS current
			DESCRIPTION
				"Description."
			::= { gponOnuObjects 1 }

		
		-- 1.3.6.1.4.1.34592.1.5.1.1.2.18.1.1
		gponOnuConfigEntry OBJECT-TYPE
			SYNTAX GponOnuConfigEntry
			MAX-ACCESS not-accessible
			STATUS current
			DESCRIPTION
				"Description."
			INDEX { gponOltDeviceId, gponOltCardId, gponOltPortId, gponOnuId }
			::= { gponOnuConfigTable 1 }

		
		GponOnuConfigEntry ::=
			SEQUENCE { 
				gponOnuId
					GponOnuId,
				gponOnuRowStatus
					RowStatus,
				gponOnuAuthMode
					INTEGER,
				gponOnuSn
					DisplayString,
				gponOnuPassword
					DisplayString,
				gponOnuLineProfileId
					GponLinePorfileId,
				gponOnuServiceProfileId
					GponSrvProfileId,
				gponOnuDescription
					DisplayString
			 }

		-- 1.3.6.1.4.1.34592.1.5.1.1.2.18.1.1.1
		gponOnuId OBJECT-TYPE
			SYNTAX GponOnuId
			MAX-ACCESS not-accessible
			STATUS current
			DESCRIPTION
				"Description."
			::= { gponOnuConfigEntry 1 }

		
		-- 1.3.6.1.4.1.34592.1.5.1.1.2.18.1.1.2
		gponOnuRowStatus OBJECT-TYPE
			SYNTAX RowStatus
			MAX-ACCESS read-create
			STATUS current
			DESCRIPTION
				"Description."
			::= { gponOnuConfigEntry 2 }

		
		-- 1.3.6.1.4.1.34592.1.5.1.1.2.18.1.1.3
		gponOnuAuthMode OBJECT-TYPE
			SYNTAX INTEGER
				{
				sn(1),
				password(2),
				sn-and-password(3)
				}
			MAX-ACCESS read-create
			STATUS current
			DESCRIPTION
				"Description."
			::= { gponOnuConfigEntry 3 }

		
		-- 1.3.6.1.4.1.34592.1.5.1.1.2.18.1.1.4
		gponOnuSn OBJECT-TYPE
			SYNTAX DisplayString
			MAX-ACCESS read-create
			STATUS current
			DESCRIPTION
				"Description."
			::= { gponOnuConfigEntry 4 }

		
		-- 1.3.6.1.4.1.34592.1.5.1.1.2.18.1.1.5
		gponOnuPassword OBJECT-TYPE
			SYNTAX DisplayString
			MAX-ACCESS read-create
			STATUS current
			DESCRIPTION
				"Description."
			::= { gponOnuConfigEntry 5 }

		
		-- 1.3.6.1.4.1.34592.1.5.1.1.2.18.1.1.6
		gponOnuLineProfileId OBJECT-TYPE
			SYNTAX GponLinePorfileId
			MAX-ACCESS read-create
			STATUS current
			DESCRIPTION
				"Description."
			::= { gponOnuConfigEntry 6 }

		
		-- 1.3.6.1.4.1.34592.1.5.1.1.2.18.1.1.7
		gponOnuServiceProfileId OBJECT-TYPE
			SYNTAX GponSrvProfileId
			MAX-ACCESS read-create
			STATUS current
			DESCRIPTION
				"Description."
			::= { gponOnuConfigEntry 7 }

		
		-- 1.3.6.1.4.1.34592.1.5.1.1.2.18.1.1.8
		gponOnuDescription OBJECT-TYPE
			SYNTAX DisplayString
			MAX-ACCESS read-create
			STATUS current
			DESCRIPTION
				"Description."
			::= { gponOnuConfigEntry 8 }

		
		-- 1.3.6.1.4.1.34592.1.5.1.1.2.18.2
		gponOnuInfoTable OBJECT-TYPE
			SYNTAX SEQUENCE OF GponOnuInfoEntry
			MAX-ACCESS not-accessible
			STATUS current
			DESCRIPTION
				"Description."
			::= { gponOnuObjects 2 }

		
		-- 1.3.6.1.4.1.34592.1.5.1.1.2.18.2.1
		gponOnuInfoEntry OBJECT-TYPE
			SYNTAX GponOnuInfoEntry
			MAX-ACCESS not-accessible
			STATUS current
			DESCRIPTION
				"Description."
			INDEX { gponOltDeviceId, gponOltCardId, gponOltPortId, gponOnuId }
			::= { gponOnuInfoTable 1 }

		
		GponOnuInfoEntry ::=
			SEQUENCE { 
				gponOnuRunState
					INTEGER,
				gponOnuConfigState
					INTEGER,
				gponOnuMatchState
					INTEGER,
				gponOnuDistance
					Integer32,
				gponOnuInfoDescription
					OCTET STRING,
				gponOnuInfoLastUpTime
					DisplayString,
				gponOnuInfoLastDownTime
					DisplayString
			 }

		-- 1.3.6.1.4.1.34592.1.5.1.1.2.18.2.1.1
		gponOnuRunState OBJECT-TYPE
			SYNTAX INTEGER
				{
				online(1),
				offline(2)
				}
			MAX-ACCESS read-only
			STATUS current
			DESCRIPTION
				"Description."
			::= { gponOnuInfoEntry 1 }

		
		-- 1.3.6.1.4.1.34592.1.5.1.1.2.18.2.1.2
		gponOnuConfigState OBJECT-TYPE
			SYNTAX INTEGER
				{
				initial(1),
				success(2),
				failed(3),
				configing(4)
				}
			MAX-ACCESS read-only
			STATUS current
			DESCRIPTION
				"Description."
			::= { gponOnuInfoEntry 2 }

		
		-- 1.3.6.1.4.1.34592.1.5.1.1.2.18.2.1.3
		gponOnuMatchState OBJECT-TYPE
			SYNTAX INTEGER
				{
				initial(1),
				match(2),
				mismatch(3)
				}
			MAX-ACCESS read-only
			STATUS current
			DESCRIPTION
				"Description."
			::= { gponOnuInfoEntry 3 }

		
		-- 1.3.6.1.4.1.34592.1.5.1.1.2.18.2.1.4
		gponOnuDistance OBJECT-TYPE
			SYNTAX Integer32
			MAX-ACCESS read-only
			STATUS current
			DESCRIPTION
				"Description."
			::= { gponOnuInfoEntry 4 }

		
		-- 1.3.6.1.4.1.34592.1.5.1.1.2.18.2.1.5
		gponOnuInfoDescription OBJECT-TYPE
			SYNTAX OCTET STRING (SIZE (0..64))
			MAX-ACCESS read-write
			STATUS current
			DESCRIPTION
				"Description."
			::= { gponOnuInfoEntry 5 }

		
		-- 1.3.6.1.4.1.34592.1.5.1.1.2.18.2.1.6
		gponOnuInfoLastUpTime OBJECT-TYPE
			SYNTAX DisplayString
			MAX-ACCESS read-only
			STATUS current
			DESCRIPTION
				"Description."
			::= { gponOnuInfoEntry 6 }

		
		-- 1.3.6.1.4.1.34592.1.5.1.1.2.18.2.1.7
		gponOnuInfoLastDownTime OBJECT-TYPE
			SYNTAX DisplayString
			MAX-ACCESS read-only
			STATUS current
			DESCRIPTION
				"Description."
			::= { gponOnuInfoEntry 7 }

		
		-- 1.3.6.1.4.1.34592.1.5.1.1.2.18.3
		gponOnuCapabilityInfoTable OBJECT-TYPE
			SYNTAX SEQUENCE OF GponOnuCapabilityInfoEntry
			MAX-ACCESS not-accessible
			STATUS current
			DESCRIPTION
				"Description."
			::= { gponOnuObjects 3 }

		
		-- 1.3.6.1.4.1.34592.1.5.1.1.2.18.3.1
		gponOnuCapabilityInfoEntry OBJECT-TYPE
			SYNTAX GponOnuCapabilityInfoEntry
			MAX-ACCESS not-accessible
			STATUS current
			DESCRIPTION
				"Description."
			INDEX { gponOltDeviceId, gponOltCardId, gponOltPortId, gponOnuId }
			::= { gponOnuCapabilityInfoTable 1 }

		
		GponOnuCapabilityInfoEntry ::=
			SEQUENCE { 
				gponOnuType
					INTEGER,
				gponOnuPonPortNum
					Integer32,
				gponOnuEthPortNum
					Integer32,
				gponOnuVeipPortNum
					Integer32,
				gponOnuPotsPortNum
					Integer32,
				gponOnuCatvPortNum
					Integer32,
				gponOnuGemPortNum
					Integer32,
				gponOnuTcontNum
					Integer32,
				gponOnuFlowControlType
					INTEGER
			 }

		-- 1.3.6.1.4.1.34592.1.5.1.1.2.18.3.1.1
		gponOnuType OBJECT-TYPE
			SYNTAX INTEGER
				{
				sfu(1),
				mdu(2),
				hgu(3),
				sfu-hgu(4),
				mdu-hgu(5)
				}
			MAX-ACCESS read-only
			STATUS current
			DESCRIPTION
				"Description."
			::= { gponOnuCapabilityInfoEntry 1 }

		
		-- 1.3.6.1.4.1.34592.1.5.1.1.2.18.3.1.2
		gponOnuPonPortNum OBJECT-TYPE
			SYNTAX Integer32
			MAX-ACCESS read-only
			STATUS current
			DESCRIPTION
				"Description."
			::= { gponOnuCapabilityInfoEntry 2 }

		
		-- 1.3.6.1.4.1.34592.1.5.1.1.2.18.3.1.3
		gponOnuEthPortNum OBJECT-TYPE
			SYNTAX Integer32
			MAX-ACCESS read-only
			STATUS current
			DESCRIPTION
				"Description."
			::= { gponOnuCapabilityInfoEntry 3 }

		
		-- 1.3.6.1.4.1.34592.1.5.1.1.2.18.3.1.4
		gponOnuVeipPortNum OBJECT-TYPE
			SYNTAX Integer32
			MAX-ACCESS read-only
			STATUS current
			DESCRIPTION
				"Description."
			::= { gponOnuCapabilityInfoEntry 4 }

		
		-- 1.3.6.1.4.1.34592.1.5.1.1.2.18.3.1.5
		gponOnuPotsPortNum OBJECT-TYPE
			SYNTAX Integer32
			MAX-ACCESS read-only
			STATUS current
			DESCRIPTION
				"Description."
			::= { gponOnuCapabilityInfoEntry 5 }

		
		-- 1.3.6.1.4.1.34592.1.5.1.1.2.18.3.1.6
		gponOnuCatvPortNum OBJECT-TYPE
			SYNTAX Integer32
			MAX-ACCESS read-only
			STATUS current
			DESCRIPTION
				"Description."
			::= { gponOnuCapabilityInfoEntry 6 }

		
		-- 1.3.6.1.4.1.34592.1.5.1.1.2.18.3.1.7
		gponOnuGemPortNum OBJECT-TYPE
			SYNTAX Integer32
			MAX-ACCESS read-only
			STATUS current
			DESCRIPTION
				"Description."
			::= { gponOnuCapabilityInfoEntry 7 }

		
		-- 1.3.6.1.4.1.34592.1.5.1.1.2.18.3.1.8
		gponOnuTcontNum OBJECT-TYPE
			SYNTAX Integer32
			MAX-ACCESS read-only
			STATUS current
			DESCRIPTION
				"Description."
			::= { gponOnuCapabilityInfoEntry 8 }

		
		-- 1.3.6.1.4.1.34592.1.5.1.1.2.18.3.1.9
		gponOnuFlowControlType OBJECT-TYPE
			SYNTAX INTEGER
				{
				pq(0),
				car(1),
				pqAndCar(2)
				}
			MAX-ACCESS read-only
			STATUS current
			DESCRIPTION
				"Description."
			::= { gponOnuCapabilityInfoEntry 9 }

		
		-- 1.3.6.1.4.1.34592.1.5.1.1.2.18.4
		gponOnuControlTable OBJECT-TYPE
			SYNTAX SEQUENCE OF GponOnuControlEntry
			MAX-ACCESS not-accessible
			STATUS current
			DESCRIPTION
				"Description."
			::= { gponOnuObjects 4 }

		
		-- 1.3.6.1.4.1.34592.1.5.1.1.2.18.4.1
		gponOnuControlEntry OBJECT-TYPE
			SYNTAX GponOnuControlEntry
			MAX-ACCESS not-accessible
			STATUS current
			DESCRIPTION
				"Description."
			INDEX { gponOltDeviceId, gponOltCardId, gponOltPortId, gponOnuId }
			::= { gponOnuControlTable 1 }

		
		GponOnuControlEntry ::=
			SEQUENCE { 
				gponOnuReset
					INTEGER,
				gponOnuDeactive
					INTEGER
			 }

		-- 1.3.6.1.4.1.34592.1.5.1.1.2.18.4.1.1
		gponOnuReset OBJECT-TYPE
			SYNTAX INTEGER
				{
				none(0),
				reset(1)
				}
			MAX-ACCESS read-write
			STATUS current
			DESCRIPTION
				"Description."
			::= { gponOnuControlEntry 1 }

		
		-- 1.3.6.1.4.1.34592.1.5.1.1.2.18.4.1.2
		gponOnuDeactive OBJECT-TYPE
			SYNTAX INTEGER
				{
				active(0),
				deactive(1)
				}
			MAX-ACCESS read-write
			STATUS current
			DESCRIPTION
				"Description."
			::= { gponOnuControlEntry 2 }

		
		-- 1.3.6.1.4.1.34592.1.5.1.1.2.18.5
		gponOnuAutofindInfoTable OBJECT-TYPE
			SYNTAX SEQUENCE OF GponOnuAutofindInfoEntry
			MAX-ACCESS not-accessible
			STATUS current
			DESCRIPTION
				"Description."
			::= { gponOnuObjects 5 }

		
		-- 1.3.6.1.4.1.34592.1.5.1.1.2.18.5.1
		gponOnuAutofindInfoEntry OBJECT-TYPE
			SYNTAX GponOnuAutofindInfoEntry
			MAX-ACCESS not-accessible
			STATUS current
			DESCRIPTION
				"Description."
			INDEX { gponOltDeviceId, gponOltCardId, gponOltPortId, gponOnuAutofindId }
			::= { gponOnuAutofindInfoTable 1 }

		
		GponOnuAutofindInfoEntry ::=
			SEQUENCE { 
				gponOnuAutofindId
					Integer32,
				gponOnuAutofindRowStatus
					INTEGER,
				gponOnuAutofindSn
					GponOnuSn,
				gponOnuAutofindPassword
					GponOnuPassword,
				gponOnuAutofindVendorId
					OCTET STRING,
				gponOnuAutofindVersion
					OCTET STRING,
				gponOnuAutofindEquipmentID
					OCTET STRING,
				gponOnuAutofindSoftwareVersion
					OCTET STRING,
				gponOnuAutofindTime
					DisplayString
			 }

		-- 1.3.6.1.4.1.34592.1.5.1.1.2.18.5.1.1
		gponOnuAutofindId OBJECT-TYPE
			SYNTAX Integer32 (1..128)
			MAX-ACCESS not-accessible
			STATUS current
			DESCRIPTION
				"Description."
			::= { gponOnuAutofindInfoEntry 1 }

		
		-- 1.3.6.1.4.1.34592.1.5.1.1.2.18.5.1.2
		gponOnuAutofindRowStatus OBJECT-TYPE
			SYNTAX INTEGER
				{
				active(1),
				destory(6)
				}
			MAX-ACCESS read-create
			STATUS current
			DESCRIPTION
				"Description."
			::= { gponOnuAutofindInfoEntry 2 }

		
		-- 1.3.6.1.4.1.34592.1.5.1.1.2.18.5.1.3
		gponOnuAutofindSn OBJECT-TYPE
			SYNTAX GponOnuSn
			MAX-ACCESS read-create
			STATUS current
			DESCRIPTION
				"Description."
			::= { gponOnuAutofindInfoEntry 3 }

		
		-- 1.3.6.1.4.1.34592.1.5.1.1.2.18.5.1.4
		gponOnuAutofindPassword OBJECT-TYPE
			SYNTAX GponOnuPassword
			MAX-ACCESS read-create
			STATUS current
			DESCRIPTION
				"Description."
			::= { gponOnuAutofindInfoEntry 4 }

		
		-- 1.3.6.1.4.1.34592.1.5.1.1.2.18.5.1.5
		gponOnuAutofindVendorId OBJECT-TYPE
			SYNTAX OCTET STRING (SIZE (4))
			MAX-ACCESS read-create
			STATUS current
			DESCRIPTION
				"Description."
			::= { gponOnuAutofindInfoEntry 5 }

		
		-- 1.3.6.1.4.1.34592.1.5.1.1.2.18.5.1.6
		gponOnuAutofindVersion OBJECT-TYPE
			SYNTAX OCTET STRING (SIZE (1..14))
			MAX-ACCESS read-create
			STATUS current
			DESCRIPTION
				"Description."
			::= { gponOnuAutofindInfoEntry 6 }

		
		-- 1.3.6.1.4.1.34592.1.5.1.1.2.18.5.1.7
		gponOnuAutofindEquipmentID OBJECT-TYPE
			SYNTAX OCTET STRING (SIZE (1..20))
			MAX-ACCESS read-create
			STATUS current
			DESCRIPTION
				"Description."
			::= { gponOnuAutofindInfoEntry 7 }

		
		-- 1.3.6.1.4.1.34592.1.5.1.1.2.18.5.1.8
		gponOnuAutofindSoftwareVersion OBJECT-TYPE
			SYNTAX OCTET STRING (SIZE (1..14))
			MAX-ACCESS read-create
			STATUS current
			DESCRIPTION
				"Description."
			::= { gponOnuAutofindInfoEntry 8 }

		
		-- 1.3.6.1.4.1.34592.1.5.1.1.2.18.5.1.9
		gponOnuAutofindTime OBJECT-TYPE
			SYNTAX DisplayString
			MAX-ACCESS read-create
			STATUS current
			DESCRIPTION
				"Description."
			::= { gponOnuAutofindInfoEntry 9 }

		
		-- 1.3.6.1.4.1.34592.1.5.1.1.2.18.6
		gponOnuOpticalInfoTable OBJECT-TYPE
			SYNTAX SEQUENCE OF GponOnuOpticalInfoEntry
			MAX-ACCESS not-accessible
			STATUS current
			DESCRIPTION
				"Description."
			::= { gponOnuObjects 6 }

		
		-- 1.3.6.1.4.1.34592.1.5.1.1.2.18.6.1
		gponOnuOpticalInfoEntry OBJECT-TYPE
			SYNTAX GponOnuOpticalInfoEntry
			MAX-ACCESS not-accessible
			STATUS current
			DESCRIPTION
				"Description."
			INDEX { gponOltDeviceId, gponOltCardId, gponOltPortId, gponOnuId }
			::= { gponOnuOpticalInfoTable 1 }

		
		GponOnuOpticalInfoEntry ::=
			SEQUENCE { 
				gponOnuOpticalVoltage
					DisplayString,
				gponOnuOpticalTxPower
					DisplayString,
				gponOnuOpticalRxPower
					DisplayString,
				gponOnuOpticalLaserBiasCurrent
					DisplayString,
				gponOnuOpticalTemperature
					DisplayString
			 }

		-- 1.3.6.1.4.1.34592.1.5.1.1.2.18.6.1.1
		gponOnuOpticalVoltage OBJECT-TYPE
			SYNTAX DisplayString
			MAX-ACCESS read-only
			STATUS current
			DESCRIPTION
				"Description."
			::= { gponOnuOpticalInfoEntry 1 }

		
		-- 1.3.6.1.4.1.34592.1.5.1.1.2.18.6.1.2
		gponOnuOpticalTxPower OBJECT-TYPE
			SYNTAX DisplayString
			MAX-ACCESS read-only
			STATUS current
			DESCRIPTION
				"Description."
			::= { gponOnuOpticalInfoEntry 2 }

		
		-- 1.3.6.1.4.1.34592.1.5.1.1.2.18.6.1.4
		gponOnuOpticalRxPower OBJECT-TYPE
			SYNTAX DisplayString
			MAX-ACCESS read-only
			STATUS current
			DESCRIPTION
				"Description."
			::= { gponOnuOpticalInfoEntry 4 }

		
		-- 1.3.6.1.4.1.34592.1.5.1.1.2.18.6.1.5
		gponOnuOpticalLaserBiasCurrent OBJECT-TYPE
			SYNTAX DisplayString
			MAX-ACCESS read-only
			STATUS current
			DESCRIPTION
				"Description."
			::= { gponOnuOpticalInfoEntry 5 }

		
		-- 1.3.6.1.4.1.34592.1.5.1.1.2.18.6.1.6
		gponOnuOpticalTemperature OBJECT-TYPE
			SYNTAX DisplayString
			MAX-ACCESS read-only
			STATUS current
			DESCRIPTION
				"Description."
			::= { gponOnuOpticalInfoEntry 6 }

		
		-- 1.3.6.1.4.1.34592.1.5.1.1.2.18.7
		gponOnuVersionTable OBJECT-TYPE
			SYNTAX SEQUENCE OF GponOnuVersionEntry
			MAX-ACCESS not-accessible
			STATUS current
			DESCRIPTION
				"Description."
			::= { gponOnuObjects 7 }

		
		-- 1.3.6.1.4.1.34592.1.5.1.1.2.18.7.1
		gponOnuVersionEntry OBJECT-TYPE
			SYNTAX GponOnuVersionEntry
			MAX-ACCESS not-accessible
			STATUS current
			DESCRIPTION
				"Description."
			INDEX { gponOltDeviceId, gponOltCardId, gponOltPortId, gponOnuId }
			::= { gponOnuVersionTable 1 }

		
		GponOnuVersionEntry ::=
			SEQUENCE { 
				gponOnuMainSoftwareVersion
					DisplayString,
				gponOnuStandbySoftwareVersion
					DisplayString
			 }

		-- 1.3.6.1.4.1.34592.1.5.1.1.2.18.7.1.1
		gponOnuMainSoftwareVersion OBJECT-TYPE
			SYNTAX DisplayString
			MAX-ACCESS read-only
			STATUS current
			DESCRIPTION
				"Description."
			::= { gponOnuVersionEntry 1 }

		
		-- 1.3.6.1.4.1.34592.1.5.1.1.2.18.7.1.2
		gponOnuStandbySoftwareVersion OBJECT-TYPE
			SYNTAX DisplayString
			MAX-ACCESS read-only
			STATUS current
			DESCRIPTION
				"Description."
			::= { gponOnuVersionEntry 2 }

		
		-- 1.3.6.1.4.1.34592.1.5.1.1.2.18.8
		gponOnuAuthenticationManagement OBJECT IDENTIFIER ::= { gponOnuObjects 8 }

		
		-- 1.3.6.1.4.1.34592.1.5.1.1.2.18.8.2
		gponOnuAuthenticationConfirmTable OBJECT-TYPE
			SYNTAX SEQUENCE OF GponOnuAuthenticationConfirmEntry
			MAX-ACCESS not-accessible
			STATUS current
			DESCRIPTION
				"Description."
			::= { gponOnuAuthenticationManagement 2 }

		
		-- 1.3.6.1.4.1.34592.1.5.1.1.2.18.8.2.1
		gponOnuAuthenticationConfirmEntry OBJECT-TYPE
			SYNTAX GponOnuAuthenticationConfirmEntry
			MAX-ACCESS not-accessible
			STATUS current
			DESCRIPTION
				"Description."
			INDEX { gponOnuAuthenticationConfirmDeviceId, gponOnuAuthenticationConfirmCardId, gponOnuAuthenticationConfirmPortId }
			::= { gponOnuAuthenticationConfirmTable 1 }

		
		GponOnuAuthenticationConfirmEntry ::=
			SEQUENCE { 
				gponOnuAuthenticationConfirmDeviceId
					Integer32,
				gponOnuAuthenticationConfirmCardId
					Integer32,
				gponOnuAuthenticationConfirmPortId
					Integer32,
				gponOnuAuthenConfirmType
					INTEGER,
				gponOnuAuthenConfirmSn
					DisplayString,
				gponOnuAuthenConfirmPassword
					DisplayString,
				gponOnuAuthenConfirmLoid
					GponOnuLoid,
				gponOnuAuthenConfirmLoidPassword
					GponOnuLoidPassword,
				gponOnuAuthenConfirmLineProfileId
					Unsigned32,
				gponOnuAuthenConfirmServiceProfileId
					Unsigned32,
				gponOnuAuthenConfirmTimeMode
					INTEGER,
				gponOnuAuthenConfirmAgingDuration
					Unsigned32,
				gponOnuAuthenticationConfirmRowStatus
					RowStatus
			 }

		-- 1.3.6.1.4.1.34592.1.5.1.1.2.18.8.2.1.1
		gponOnuAuthenticationConfirmDeviceId OBJECT-TYPE
			SYNTAX Integer32
			MAX-ACCESS not-accessible
			STATUS current
			DESCRIPTION
				"Description."
			::= { gponOnuAuthenticationConfirmEntry 1 }

		
		-- 1.3.6.1.4.1.34592.1.5.1.1.2.18.8.2.1.2
		gponOnuAuthenticationConfirmCardId OBJECT-TYPE
			SYNTAX Integer32
			MAX-ACCESS not-accessible
			STATUS current
			DESCRIPTION
				"Description."
			::= { gponOnuAuthenticationConfirmEntry 2 }

		
		-- 1.3.6.1.4.1.34592.1.5.1.1.2.18.8.2.1.3
		gponOnuAuthenticationConfirmPortId OBJECT-TYPE
			SYNTAX Integer32
			MAX-ACCESS not-accessible
			STATUS current
			DESCRIPTION
				"Description."
			::= { gponOnuAuthenticationConfirmEntry 3 }

		
		-- 1.3.6.1.4.1.34592.1.5.1.1.2.18.8.2.1.4
		gponOnuAuthenConfirmType OBJECT-TYPE
			SYNTAX INTEGER
				{
				snAuth(1),
				snPwdAuth(2),
				pwdAuth(3),
				loidAuth(4),
				loidPwdAuth(5),
				snAuthAll(6),
				snPwdAuthAll(7),
				pwdAuthAll(8),
				loidAuthAll(9),
				loidPwdAuthAll(10)
				}
			MAX-ACCESS read-create
			STATUS current
			DESCRIPTION
				"Description."
			::= { gponOnuAuthenticationConfirmEntry 4 }

		
		-- 1.3.6.1.4.1.34592.1.5.1.1.2.18.8.2.1.5
		gponOnuAuthenConfirmSn OBJECT-TYPE
			SYNTAX DisplayString
			MAX-ACCESS read-create
			STATUS current
			DESCRIPTION
				"Description."
			::= { gponOnuAuthenticationConfirmEntry 5 }

		
		-- 1.3.6.1.4.1.34592.1.5.1.1.2.18.8.2.1.6
		gponOnuAuthenConfirmPassword OBJECT-TYPE
			SYNTAX DisplayString
			MAX-ACCESS read-create
			STATUS current
			DESCRIPTION
				"Description."
			::= { gponOnuAuthenticationConfirmEntry 6 }

		
		-- 1.3.6.1.4.1.34592.1.5.1.1.2.18.8.2.1.7
		gponOnuAuthenConfirmLoid OBJECT-TYPE
			SYNTAX GponOnuLoid
			MAX-ACCESS read-create
			STATUS current
			DESCRIPTION
				"Description."
			::= { gponOnuAuthenticationConfirmEntry 7 }

		
		-- 1.3.6.1.4.1.34592.1.5.1.1.2.18.8.2.1.8
		gponOnuAuthenConfirmLoidPassword OBJECT-TYPE
			SYNTAX GponOnuLoidPassword
			MAX-ACCESS read-create
			STATUS current
			DESCRIPTION
				"Description."
			::= { gponOnuAuthenticationConfirmEntry 8 }

		
		-- 1.3.6.1.4.1.34592.1.5.1.1.2.18.8.2.1.9
		gponOnuAuthenConfirmLineProfileId OBJECT-TYPE
			SYNTAX Unsigned32
			MAX-ACCESS read-create
			STATUS current
			DESCRIPTION
				"Description."
			::= { gponOnuAuthenticationConfirmEntry 9 }

		
		-- 1.3.6.1.4.1.34592.1.5.1.1.2.18.8.2.1.10
		gponOnuAuthenConfirmServiceProfileId OBJECT-TYPE
			SYNTAX Unsigned32
			MAX-ACCESS read-create
			STATUS current
			DESCRIPTION
				"Description."
			::= { gponOnuAuthenticationConfirmEntry 10 }

		
		-- 1.3.6.1.4.1.34592.1.5.1.1.2.18.8.2.1.11
		gponOnuAuthenConfirmTimeMode OBJECT-TYPE
			SYNTAX INTEGER
				{
				always(0),
				onceAging(1),
				onceNoAging(2)
				}
			MAX-ACCESS read-create
			STATUS current
			DESCRIPTION
				"Description."
			::= { gponOnuAuthenticationConfirmEntry 11 }

		
		-- 1.3.6.1.4.1.34592.1.5.1.1.2.18.8.2.1.12
		gponOnuAuthenConfirmAgingDuration OBJECT-TYPE
			SYNTAX Unsigned32
			MAX-ACCESS read-create
			STATUS current
			DESCRIPTION
				"Description."
			::= { gponOnuAuthenticationConfirmEntry 12 }

		
		-- 1.3.6.1.4.1.34592.1.5.1.1.2.18.8.2.1.13
		gponOnuAuthenticationConfirmRowStatus OBJECT-TYPE
			SYNTAX RowStatus
			MAX-ACCESS read-create
			STATUS current
			DESCRIPTION
				"Description."
			::= { gponOnuAuthenticationConfirmEntry 13 }

		
		-- 1.3.6.1.4.1.34592.1.5.1.1.2.18.8.3
		gponOnuPolicyAuthTable OBJECT IDENTIFIER ::= { gponOnuAuthenticationManagement 3 }

		
		-- 1.3.6.1.4.1.34592.1.5.1.1.2.18.8.3.1
		gponOnuPolicyAuthControlTable OBJECT-TYPE
			SYNTAX SEQUENCE OF GponOnuPolicyAuthControlEntry
			MAX-ACCESS not-accessible
			STATUS current
			DESCRIPTION
				"Description."
			::= { gponOnuPolicyAuthTable 1 }

		
		-- 1.3.6.1.4.1.34592.1.5.1.1.2.18.8.3.1.1
		gponOnuPolicyAuthControlEntry OBJECT-TYPE
			SYNTAX GponOnuPolicyAuthControlEntry
			MAX-ACCESS not-accessible
			STATUS current
			DESCRIPTION
				"Description."
			INDEX { gponOnuPolicyAuthControlDeviceIndex }
			::= { gponOnuPolicyAuthControlTable 1 }

		
		GponOnuPolicyAuthControlEntry ::=
			SEQUENCE { 
				gponOnuPolicyAuthControlDeviceIndex
					Integer32,
				gponOnuPolicyAuthSwitch
					GponSwitch,
				gponOnuPolicyAuthPortSwtichBitMap
					OCTET STRING,
				gponOnuPolicyAuthMode
					INTEGER,
				gponOnuPolicyAuthTargetMode
					INTEGER,
				gponOnuPolicyAuthTimeMode
					INTEGER
			 }

		-- 1.3.6.1.4.1.34592.1.5.1.1.2.18.8.3.1.1.1
		gponOnuPolicyAuthControlDeviceIndex OBJECT-TYPE
			SYNTAX Integer32
			MAX-ACCESS not-accessible
			STATUS current
			DESCRIPTION
				"Description."
			::= { gponOnuPolicyAuthControlEntry 1 }

		
		-- 1.3.6.1.4.1.34592.1.5.1.1.2.18.8.3.1.1.2
		gponOnuPolicyAuthSwitch OBJECT-TYPE
			SYNTAX GponSwitch
			MAX-ACCESS read-write
			STATUS current
			DESCRIPTION
				"Description."
			::= { gponOnuPolicyAuthControlEntry 2 }

		
		-- 1.3.6.1.4.1.34592.1.5.1.1.2.18.8.3.1.1.3
		gponOnuPolicyAuthPortSwtichBitMap OBJECT-TYPE
			SYNTAX OCTET STRING (SIZE (0..16))
			MAX-ACCESS read-write
			STATUS current
			DESCRIPTION
				"Description."
			::= { gponOnuPolicyAuthControlEntry 3 }

		
		-- 1.3.6.1.4.1.34592.1.5.1.1.2.18.8.3.1.1.4
		gponOnuPolicyAuthMode OBJECT-TYPE
			SYNTAX INTEGER
				{
				all(0),
				equid(1),
				vendor(2),
				equidAndSwver(3)
				}
			MAX-ACCESS read-write
			STATUS current
			DESCRIPTION
				"Description."
			::= { gponOnuPolicyAuthControlEntry 4 }

		
		-- 1.3.6.1.4.1.34592.1.5.1.1.2.18.8.3.1.1.5
		gponOnuPolicyAuthTargetMode OBJECT-TYPE
			SYNTAX INTEGER
				{
				snAuth(0),
				snPasswordAuth(1),
				passwordAuth(2),
				loidAuth(3),
				loidPasswordAuth(4)
				}
			MAX-ACCESS read-write
			STATUS current
			DESCRIPTION
				"Description."
			::= { gponOnuPolicyAuthControlEntry 5 }

		
		-- 1.3.6.1.4.1.34592.1.5.1.1.2.18.8.3.1.1.6
		gponOnuPolicyAuthTimeMode OBJECT-TYPE
			SYNTAX INTEGER
				{
				always(0),
				onceNoAging(1)
				}
			MAX-ACCESS read-write
			STATUS current
			DESCRIPTION
				"Description."
			::= { gponOnuPolicyAuthControlEntry 6 }

		
		-- 1.3.6.1.4.1.34592.1.5.1.1.2.18.8.3.2
		gponOnuPolicyAuthRuleTable OBJECT-TYPE
			SYNTAX SEQUENCE OF GponOnuPolicyAuthRuleEntry
			MAX-ACCESS not-accessible
			STATUS current
			DESCRIPTION
				"Description."
			::= { gponOnuPolicyAuthTable 2 }

		
		-- 1.3.6.1.4.1.34592.1.5.1.1.2.18.8.3.2.1
		gponOnuPolicyAuthRuleEntry OBJECT-TYPE
			SYNTAX GponOnuPolicyAuthRuleEntry
			MAX-ACCESS not-accessible
			STATUS current
			DESCRIPTION
				"Description."
			INDEX { gponOnuPolicyAuthDeviceIndex, gponOnuPolicyAuthRuleIndex }
			::= { gponOnuPolicyAuthRuleTable 1 }

		
		GponOnuPolicyAuthRuleEntry ::=
			SEQUENCE { 
				gponOnuPolicyAuthDeviceIndex
					Unsigned32,
				gponOnuPolicyAuthRuleIndex
					Unsigned32,
				gponOnuPolicyAuthRuleMatchMode
					INTEGER,
				gponOnuPolicyAuthRuleEquid
					OCTET STRING,
				gponOnuPolicyAuthRuleVendorid
					OCTET STRING,
				gponOnuPolicyAuthRuleSoftwareVersion
					OCTET STRING,
				gponOnuPolicyAuthRuleLineProfileId
					Unsigned32,
				gponOnuPolicyAuthRuleSrvProfileId
					Unsigned32,
				gponOnuPolicyAuthRuleRowStatus
					RowStatus,
				gponOnuPolicyAuthRulePortId
					Integer32,
				gponOnuPolicyAuthRuleOntList
					OCTET STRING,
				gponOnuPolicyAuthRuleOntTypeProfile
					Integer32
			 }

		-- 1.3.6.1.4.1.34592.1.5.1.1.2.18.8.3.2.1.1
		gponOnuPolicyAuthDeviceIndex OBJECT-TYPE
			SYNTAX Unsigned32
			MAX-ACCESS not-accessible
			STATUS current
			DESCRIPTION
				"Description."
			::= { gponOnuPolicyAuthRuleEntry 1 }

		
		-- 1.3.6.1.4.1.34592.1.5.1.1.2.18.8.3.2.1.2
		gponOnuPolicyAuthRuleIndex OBJECT-TYPE
			SYNTAX Unsigned32
			MAX-ACCESS not-accessible
			STATUS current
			DESCRIPTION
				"Description."
			::= { gponOnuPolicyAuthRuleEntry 2 }

		
		-- 1.3.6.1.4.1.34592.1.5.1.1.2.18.8.3.2.1.3
		gponOnuPolicyAuthRuleMatchMode OBJECT-TYPE
			SYNTAX INTEGER
				{
				ont(0),
				equidAndSwver(1),
				equid(2),
				vendor(3),
				all(4),
				ont-type(5)
				}
			MAX-ACCESS accessible-for-notify
			STATUS current
			DESCRIPTION
				"Description."
			::= { gponOnuPolicyAuthRuleEntry 3 }

		
		-- 1.3.6.1.4.1.34592.1.5.1.1.2.18.8.3.2.1.4
		gponOnuPolicyAuthRuleEquid OBJECT-TYPE
			SYNTAX OCTET STRING (SIZE (1..20))
			MAX-ACCESS read-create
			STATUS current
			DESCRIPTION
				"Description."
			::= { gponOnuPolicyAuthRuleEntry 4 }

		
		-- 1.3.6.1.4.1.34592.1.5.1.1.2.18.8.3.2.1.5
		gponOnuPolicyAuthRuleVendorid OBJECT-TYPE
			SYNTAX OCTET STRING (SIZE (4))
			MAX-ACCESS read-create
			STATUS current
			DESCRIPTION
				"Description."
			::= { gponOnuPolicyAuthRuleEntry 5 }

		
		-- 1.3.6.1.4.1.34592.1.5.1.1.2.18.8.3.2.1.6
		gponOnuPolicyAuthRuleSoftwareVersion OBJECT-TYPE
			SYNTAX OCTET STRING (SIZE (1..14))
			MAX-ACCESS read-create
			STATUS current
			DESCRIPTION
				"Description."
			::= { gponOnuPolicyAuthRuleEntry 6 }

		
		-- 1.3.6.1.4.1.34592.1.5.1.1.2.18.8.3.2.1.7
		gponOnuPolicyAuthRuleLineProfileId OBJECT-TYPE
			SYNTAX Unsigned32
			MAX-ACCESS read-create
			STATUS current
			DESCRIPTION
				"Description."
			::= { gponOnuPolicyAuthRuleEntry 7 }

		
		-- 1.3.6.1.4.1.34592.1.5.1.1.2.18.8.3.2.1.8
		gponOnuPolicyAuthRuleSrvProfileId OBJECT-TYPE
			SYNTAX Unsigned32
			MAX-ACCESS read-create
			STATUS current
			DESCRIPTION
				"Description."
			::= { gponOnuPolicyAuthRuleEntry 8 }

		
		-- 1.3.6.1.4.1.34592.1.5.1.1.2.18.8.3.2.1.9
		gponOnuPolicyAuthRuleRowStatus OBJECT-TYPE
			SYNTAX RowStatus
			MAX-ACCESS read-create
			STATUS current
			DESCRIPTION
				"Description."
			::= { gponOnuPolicyAuthRuleEntry 9 }

		
		-- 1.3.6.1.4.1.34592.1.5.1.1.2.18.8.3.2.1.10
		gponOnuPolicyAuthRulePortId OBJECT-TYPE
			SYNTAX Integer32 (1..16)
			MAX-ACCESS read-create
			STATUS current
			DESCRIPTION
				"Description."
			::= { gponOnuPolicyAuthRuleEntry 10 }

		
		-- 1.3.6.1.4.1.34592.1.5.1.1.2.18.8.3.2.1.11
		gponOnuPolicyAuthRuleOntList OBJECT-TYPE
			SYNTAX OCTET STRING
			MAX-ACCESS read-create
			STATUS current
			DESCRIPTION
				"Description."
			::= { gponOnuPolicyAuthRuleEntry 11 }

		
		-- 1.3.6.1.4.1.34592.1.5.1.1.2.18.8.3.2.1.12
		gponOnuPolicyAuthRuleOntTypeProfile OBJECT-TYPE
			SYNTAX Integer32 (1..128)
			MAX-ACCESS read-create
			STATUS current
			DESCRIPTION
				"Description."
			::= { gponOnuPolicyAuthRuleEntry 12 }

		
		-- 1.3.6.1.4.1.34592.1.5.1.1.2.18.8.4
		gponOnuAuthenticationCancelTable OBJECT-TYPE
			SYNTAX SEQUENCE OF GponOnuAuthenticationCancelEntry
			MAX-ACCESS not-accessible
			STATUS current
			DESCRIPTION
				"Description."
			::= { gponOnuAuthenticationManagement 4 }

		
		-- 1.3.6.1.4.1.34592.1.5.1.1.2.18.8.4.1
		gponOnuAuthenticationCancelEntry OBJECT-TYPE
			SYNTAX GponOnuAuthenticationCancelEntry
			MAX-ACCESS not-accessible
			STATUS current
			DESCRIPTION
				"Description."
			INDEX { gponOltPortId }
			::= { gponOnuAuthenticationCancelTable 1 }

		
		GponOnuAuthenticationCancelEntry ::=
			SEQUENCE { 
				gponOnuAuthenticationCancelSN
					OCTET STRING
			 }

		-- 1.3.6.1.4.1.34592.1.5.1.1.2.18.8.4.1.1
		gponOnuAuthenticationCancelSN OBJECT-TYPE
			SYNTAX OCTET STRING
			MAX-ACCESS read-write
			STATUS current
			DESCRIPTION
				"Description."
			::= { gponOnuAuthenticationCancelEntry 1 }


		
		-- 1.3.6.1.4.1.34592.1.5.1.1.2.18.9
		gponOnuWanConfig OBJECT IDENTIFIER ::= { gponOnuObjects 9 }

		
		-- 1.3.6.1.4.1.34592.1.5.1.1.2.18.9.1
		gponOnuWanConfigInfoTable OBJECT-TYPE
			SYNTAX SEQUENCE OF GponOnuWanConfigInfoEntry
			MAX-ACCESS not-accessible
			STATUS current
			DESCRIPTION
				"Description."
			::= { gponOnuWanConfig 1 }

		
		-- 1.3.6.1.4.1.34592.1.5.1.1.2.18.9.1.1
		gponOnuWanConfigInfoEntry OBJECT-TYPE
			SYNTAX GponOnuWanConfigInfoEntry
			MAX-ACCESS not-accessible
			STATUS current
			DESCRIPTION
				"Description."
			INDEX { gponOltDeviceId, gponOltCardId, gponOltPortId, gponOnuId, gponOnuWanInfoWanId
				 }
			::= { gponOnuWanConfigInfoTable 1 }

		
		GponOnuWanConfigInfoEntry ::=
			SEQUENCE { 
				gponOnuWanInfoWanId
					Integer32,
				gponOnuWanConfigConnectionName
					DisplayString,
				gponOnuWanConfigConnectionStatus
					INTEGER,
				gponOnuWanConfigConnectionAdmin
					GponSwitch,
				gponOnuWanConfigConnectType
					INTEGER,
				gponOnuWanConfigConnectMode
					INTEGER,
				gponOnuWanConfigIpVersion
					INTEGER,
				gponOnuWanConfigVlanAdmin
					INTEGER,
				gponOnuWanConfigVlan
					Integer32,
				gponOnuWanConfigVlanPriority
					Integer32,
				gponOnuWanConfigServiceType
					INTEGER,
				gponOnuWanConfigMtu
					Integer32,
				gponOnuWanConfigNatAdmin
					GponSwitch,
				gponOnuWanConfigLanDhcpAdmin
					GponSwitch,
				gponOnuWanConfigBinding
					BITS,
				gponOnuWanConfigPppoeUserName
					DisplayString,
				gponOnuWanConfigPppoePassWord
					DisplayString,
				gponOnuWanConfigPppoeServiceName
					DisplayString,
				gponOnuWanConfigPppoeDialOnDemandAdmin
					INTEGER,
				gponOnuWanConfigPppoeDialOnDemandInActiveTime
					Integer32,
				gponOnuWanConfigRowStatus
					RowStatus
			 }

		-- 1.3.6.1.4.1.34592.1.5.1.1.2.18.9.1.1.1
		gponOnuWanInfoWanId OBJECT-TYPE
			SYNTAX Integer32 (0..32)
			MAX-ACCESS not-accessible
			STATUS current
			DESCRIPTION
				"Description."
			::= { gponOnuWanConfigInfoEntry 1 }

		
		-- 1.3.6.1.4.1.34592.1.5.1.1.2.18.9.1.1.2
		gponOnuWanConfigConnectionName OBJECT-TYPE
			SYNTAX DisplayString (SIZE (1..50))
			MAX-ACCESS read-only
			STATUS current
			DESCRIPTION
				"Description."
			::= { gponOnuWanConfigInfoEntry 2 }

		
		-- 1.3.6.1.4.1.34592.1.5.1.1.2.18.9.1.1.3
		gponOnuWanConfigConnectionStatus OBJECT-TYPE
			SYNTAX INTEGER
				{
				down(0),
				up(1)
				}
			MAX-ACCESS read-only
			STATUS current
			DESCRIPTION
				"Description."
			::= { gponOnuWanConfigInfoEntry 3 }

		
		-- 1.3.6.1.4.1.34592.1.5.1.1.2.18.9.1.1.4
		gponOnuWanConfigConnectionAdmin OBJECT-TYPE
			SYNTAX GponSwitch
				{
				disable(0),
				enable(1)
				}
			MAX-ACCESS read-write
			STATUS current
			DESCRIPTION
				"Description."
			::= { gponOnuWanConfigInfoEntry 4 }

		
		-- 1.3.6.1.4.1.34592.1.5.1.1.2.18.9.1.1.5
		gponOnuWanConfigConnectType OBJECT-TYPE
			SYNTAX INTEGER
				{
				bridge(1),
				route(2)
				}
			MAX-ACCESS read-write
			STATUS current
			DESCRIPTION
				"Description."
			::= { gponOnuWanConfigInfoEntry 5 }

		
		-- 1.3.6.1.4.1.34592.1.5.1.1.2.18.9.1.1.6
		gponOnuWanConfigConnectMode OBJECT-TYPE
			SYNTAX INTEGER
				{
				dhcp(1),
				static(2),
				pppoe(3),
				pppoebridge(4),
				pppoemix(5)
				}
			MAX-ACCESS read-write
			STATUS current
			DESCRIPTION
				"Description."
			::= { gponOnuWanConfigInfoEntry 6 }

		
		-- 1.3.6.1.4.1.34592.1.5.1.1.2.18.9.1.1.7
		gponOnuWanConfigIpVersion OBJECT-TYPE
			SYNTAX INTEGER
				{
				ipv4(1),
				ipv6(2),
				ipv4-ipv6(3)
				}
			MAX-ACCESS read-write
			STATUS current
			DESCRIPTION
				"Description."
			::= { gponOnuWanConfigInfoEntry 7 }

		
		-- 1.3.6.1.4.1.34592.1.5.1.1.2.18.9.1.1.8
		gponOnuWanConfigVlanAdmin OBJECT-TYPE
			SYNTAX INTEGER
				{
				disable(0),
				enable(1)
				}
			MAX-ACCESS read-write
			STATUS current
			DESCRIPTION
				"Description."
			::= { gponOnuWanConfigInfoEntry 8 }

		
		-- 1.3.6.1.4.1.34592.1.5.1.1.2.18.9.1.1.9
		gponOnuWanConfigVlan OBJECT-TYPE
			SYNTAX Integer32 (1..4094)
			MAX-ACCESS read-write
			STATUS current
			DESCRIPTION
				"Description."
			::= { gponOnuWanConfigInfoEntry 9 }

		
		-- 1.3.6.1.4.1.34592.1.5.1.1.2.18.9.1.1.10
		gponOnuWanConfigVlanPriority OBJECT-TYPE
			SYNTAX Integer32 (0..7)
			MAX-ACCESS read-write
			STATUS current
			DESCRIPTION
				"Description."
			::= { gponOnuWanConfigInfoEntry 10 }

		
		-- 1.3.6.1.4.1.34592.1.5.1.1.2.18.9.1.1.11
		gponOnuWanConfigServiceType OBJECT-TYPE
			SYNTAX INTEGER
				{
				internet(1),
				voip(2),
				internet-voip(3),
				tr069(4),
				internet-tr069(5),
				voip-tr069(6),
				internet-voip-tr069(7),
				other(8)
				}
			MAX-ACCESS read-write
			STATUS current
			DESCRIPTION
				"Description."
			::= { gponOnuWanConfigInfoEntry 11 }

		
		-- 1.3.6.1.4.1.34592.1.5.1.1.2.18.9.1.1.12
		gponOnuWanConfigMtu OBJECT-TYPE
			SYNTAX Integer32 (64..1540)
			MAX-ACCESS read-write
			STATUS current
			DESCRIPTION
				"Description."
			::= { gponOnuWanConfigInfoEntry 12 }

		
		-- 1.3.6.1.4.1.34592.1.5.1.1.2.18.9.1.1.13
		gponOnuWanConfigNatAdmin OBJECT-TYPE
			SYNTAX GponSwitch
				{
				disable(0),
				enable(1)
				}
			MAX-ACCESS read-write
			STATUS current
			DESCRIPTION
				"Description."
			::= { gponOnuWanConfigInfoEntry 13 }

		
		-- 1.3.6.1.4.1.34592.1.5.1.1.2.18.9.1.1.14
		gponOnuWanConfigLanDhcpAdmin OBJECT-TYPE
			SYNTAX GponSwitch
				{
				disable(0),
				enable(1)
				}
			MAX-ACCESS read-write
			STATUS current
			DESCRIPTION
				"Description."
			::= { gponOnuWanConfigInfoEntry 14 }

		
		-- 1.3.6.1.4.1.34592.1.5.1.1.2.18.9.1.1.15
		gponOnuWanConfigBinding OBJECT-TYPE
			SYNTAX BITS
				{
				port1(0),
				port2(1),
				port3(2),
				port4(3),
				ssid1(8),
				ssid2(9),
				ssid3(10),
				ssid4(11)
				}
			MAX-ACCESS read-write
			STATUS current
			DESCRIPTION
				"0x00 01 ----- port1  0x00 02 ----- port2 
				0x00 04 ----- port3  0x00 08 ----- port4 
				0x01 00 ----- ssid1  0x02 00 ----- ssid2
				0x04 00 ----- ssid3  0x08 00 ----- ssid4   
				other-----reserve.
				"
			::= { gponOnuWanConfigInfoEntry 15 }

		
		-- 1.3.6.1.4.1.34592.1.5.1.1.2.18.9.1.1.16
		gponOnuWanConfigPppoeUserName OBJECT-TYPE
			SYNTAX DisplayString (SIZE (1..50))
			MAX-ACCESS read-write
			STATUS current
			DESCRIPTION
				"Description."
			::= { gponOnuWanConfigInfoEntry 16 }

		
		-- 1.3.6.1.4.1.34592.1.5.1.1.2.18.9.1.1.17
		gponOnuWanConfigPppoePassWord OBJECT-TYPE
			SYNTAX DisplayString (SIZE (1..50))
			MAX-ACCESS read-write
			STATUS current
			DESCRIPTION
				"Description."
			::= { gponOnuWanConfigInfoEntry 17 }

		
		-- 1.3.6.1.4.1.34592.1.5.1.1.2.18.9.1.1.18
		gponOnuWanConfigPppoeServiceName OBJECT-TYPE
			SYNTAX DisplayString (SIZE (1..50))
			MAX-ACCESS read-write
			STATUS current
			DESCRIPTION
				"Description."
			::= { gponOnuWanConfigInfoEntry 18 }

		
		-- 1.3.6.1.4.1.34592.1.5.1.1.2.18.9.1.1.19
		gponOnuWanConfigPppoeDialOnDemandAdmin OBJECT-TYPE
			SYNTAX INTEGER
				{
				disable(0),
				enable(1)
				}
			MAX-ACCESS read-write
			STATUS current
			DESCRIPTION
				"Description."
			::= { gponOnuWanConfigInfoEntry 19 }

		
		-- 1.3.6.1.4.1.34592.1.5.1.1.2.18.9.1.1.20
		gponOnuWanConfigPppoeDialOnDemandInActiveTime OBJECT-TYPE
			SYNTAX Integer32 (0..65535)
			MAX-ACCESS read-write
			STATUS current
			DESCRIPTION
				"Description."
			::= { gponOnuWanConfigInfoEntry 20 }

		
		-- 1.3.6.1.4.1.34592.1.5.1.1.2.18.9.1.1.21
		gponOnuWanConfigRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { gponOnuWanConfigInfoEntry 21 }

		
		-- 1.3.6.1.4.1.34592.1.5.1.1.2.18.9.3
		gponOnuWanConfigIpv4Table OBJECT-TYPE
			SYNTAX SEQUENCE OF GponOnuWanConfigIpv4Entry
			MAX-ACCESS not-accessible
			STATUS current
			DESCRIPTION
				"Description."
			::= { gponOnuWanConfig 3 }

		
		-- 1.3.6.1.4.1.34592.1.5.1.1.2.18.9.3.1
		gponOnuWanConfigIpv4Entry OBJECT-TYPE
			SYNTAX GponOnuWanConfigIpv4Entry
			MAX-ACCESS not-accessible
			STATUS current
			DESCRIPTION
				"Description."
			INDEX { gponOltDeviceId, gponOltCardId, gponOltPortId, gponOnuId, gponOnuWanInfoWanId
				 }
			::= { gponOnuWanConfigIpv4Table 1 }

		
		GponOnuWanConfigIpv4Entry ::=
			SEQUENCE { 
				gponOnuWanConfigIpAddress
					IpAddress,
				gponOnuWanConfigMask
					IpAddress,
				gponOnuWanConfigGateWay
					IpAddress,
				gponOnuWanConfigDhcpDnsMode
					INTEGER,
				gponOnuWanConfigPrimaryDns
					IpAddress,
				gponOnuWanConfigSecondaryDns
					IpAddress
			 }

		-- 1.3.6.1.4.1.34592.1.5.1.1.2.18.9.3.1.1
		gponOnuWanConfigIpAddress OBJECT-TYPE
			SYNTAX IpAddress
			MAX-ACCESS read-write
			STATUS current
			DESCRIPTION
				"Description."
			::= { gponOnuWanConfigIpv4Entry 1 }

		
		-- 1.3.6.1.4.1.34592.1.5.1.1.2.18.9.3.1.2
		gponOnuWanConfigMask OBJECT-TYPE
			SYNTAX IpAddress
			MAX-ACCESS read-write
			STATUS current
			DESCRIPTION
				"Description."
			::= { gponOnuWanConfigIpv4Entry 2 }

		
		-- 1.3.6.1.4.1.34592.1.5.1.1.2.18.9.3.1.3
		gponOnuWanConfigGateWay OBJECT-TYPE
			SYNTAX IpAddress
			MAX-ACCESS read-write
			STATUS current
			DESCRIPTION
				"Description."
			::= { gponOnuWanConfigIpv4Entry 3 }

		
		-- 1.3.6.1.4.1.34592.1.5.1.1.2.18.9.3.1.4
		gponOnuWanConfigDhcpDnsMode OBJECT-TYPE
			SYNTAX INTEGER
				{
				manual(0),
				autoget(1)
				}
			MAX-ACCESS read-write
			STATUS current
			DESCRIPTION
				"Description."
			::= { gponOnuWanConfigIpv4Entry 4 }

		
		-- 1.3.6.1.4.1.34592.1.5.1.1.2.18.9.3.1.5
		gponOnuWanConfigPrimaryDns OBJECT-TYPE
			SYNTAX IpAddress
			MAX-ACCESS read-write
			STATUS current
			DESCRIPTION
				"Description."
			::= { gponOnuWanConfigIpv4Entry 5 }

		
		-- 1.3.6.1.4.1.34592.1.5.1.1.2.18.9.3.1.6
		gponOnuWanConfigSecondaryDns OBJECT-TYPE
			SYNTAX IpAddress
			MAX-ACCESS read-write
			STATUS current
			DESCRIPTION
				"Description."
			::= { gponOnuWanConfigIpv4Entry 6 }

		
		-- 1.3.6.1.4.1.34592.1.5.1.1.2.18.10
		gponOnuBindOperation OBJECT IDENTIFIER ::= { gponOnuObjects 10 }

		
		-- 1.3.6.1.4.1.34592.1.5.1.1.2.18.10.1
		gponOnuBindOperationTable OBJECT-TYPE
			SYNTAX SEQUENCE OF GponOnuBindOperationEntry
			MAX-ACCESS not-accessible
			STATUS current
			DESCRIPTION
				"Description."
			::= { gponOnuBindOperation 1 }

		
		-- 1.3.6.1.4.1.34592.1.5.1.1.2.18.10.1.1
		gponOnuBindOperationEntry OBJECT-TYPE
			SYNTAX GponOnuBindOperationEntry
			MAX-ACCESS not-accessible
			STATUS current
			DESCRIPTION
				"Description."
			INDEX { gponOltDeviceId, gponOltCardId, gponOltPortId, gponOnuId }
			::= { gponOnuBindOperationTable 1 }

		
		GponOnuBindOperationEntry ::=
			SEQUENCE { 
				gponOnuBindTr069ProfileId
					Integer32,
				gponOnuBindTr069ProfileName
					OCTET STRING,
				gponOnuBindOperationRowStatus
					RowStatus
			 }

		-- 1.3.6.1.4.1.34592.1.5.1.1.2.18.10.1.1.1
		gponOnuBindTr069ProfileId OBJECT-TYPE
			SYNTAX Integer32 (1..32)
			MAX-ACCESS read-create
			STATUS current
			DESCRIPTION
				"Description."
			::= { gponOnuBindOperationEntry 1 }

		
		-- 1.3.6.1.4.1.34592.1.5.1.1.2.18.10.1.1.2
		gponOnuBindTr069ProfileName OBJECT-TYPE
			SYNTAX OCTET STRING (SIZE (1..32))
			MAX-ACCESS read-create
			STATUS current
			DESCRIPTION
				"Description."
			::= { gponOnuBindOperationEntry 2 }

		
		-- 1.3.6.1.4.1.34592.1.5.1.1.2.18.10.1.1.3
		gponOnuBindOperationRowStatus OBJECT-TYPE
			SYNTAX RowStatus
			MAX-ACCESS read-create
			STATUS current
			DESCRIPTION
				"Description."
			::= { gponOnuBindOperationEntry 3 }

		
		-- 1.3.6.1.4.1.34592.1.5.1.1.2.18.11
		gponOnuMacAddressTable OBJECT-TYPE
			SYNTAX SEQUENCE OF GponOnuMacAddressEntry
			MAX-ACCESS not-accessible
			STATUS current
			DESCRIPTION
				"Description."
			::= { gponOnuObjects 11 }

		
		-- 1.3.6.1.4.1.34592.1.5.1.1.2.18.11.1
		gponOnuMacAddressEntry OBJECT-TYPE
			SYNTAX GponOnuMacAddressEntry
			MAX-ACCESS not-accessible
			STATUS current
			DESCRIPTION
				"Description."
			INDEX { gponOltDeviceId, gponOltCardId, gponOltPortId, gponOnuId, gponOnuMacAddressOnuEthPort, 
				gponOnuMacAddressIndex }
			::= { gponOnuMacAddressTable 1 }

		
		GponOnuMacAddressEntry ::=
			SEQUENCE { 
				gponOnuMacAddressIndex
					Integer32,
				gponOnuMacAddressOnuPortType
					INTEGER,
				gponOnuMacAddressOnuEthPort
					Integer32,
				gponOnuMacAddressVlanIndex
					Integer32,
				gponOnuMacAddress
					GponMac
			 }

		-- 1.3.6.1.4.1.34592.1.5.1.1.2.18.11.1.1
		gponOnuMacAddressIndex OBJECT-TYPE
			SYNTAX Integer32
			MAX-ACCESS not-accessible
			STATUS current
			DESCRIPTION
				"Description."
			::= { gponOnuMacAddressEntry 1 }

		
		-- 1.3.6.1.4.1.34592.1.5.1.1.2.18.11.1.2
		gponOnuMacAddressOnuPortType OBJECT-TYPE
			SYNTAX INTEGER { eth(1) }
			MAX-ACCESS read-only
			STATUS current
			DESCRIPTION
				"Description."
			::= { gponOnuMacAddressEntry 2 }

		
		-- 1.3.6.1.4.1.34592.1.5.1.1.2.18.11.1.3
		gponOnuMacAddressOnuEthPort OBJECT-TYPE
			SYNTAX Integer32
			MAX-ACCESS not-accessible
			STATUS current
			DESCRIPTION
				"Description."
			::= { gponOnuMacAddressEntry 3 }

		
		-- 1.3.6.1.4.1.34592.1.5.1.1.2.18.11.1.4
		gponOnuMacAddressVlanIndex OBJECT-TYPE
			SYNTAX Integer32
			MAX-ACCESS read-only
			STATUS current
			DESCRIPTION
				"Description."
			::= { gponOnuMacAddressEntry 4 }

		
		-- 1.3.6.1.4.1.34592.1.5.1.1.2.18.11.1.5
		gponOnuMacAddress OBJECT-TYPE
			SYNTAX GponMac
			MAX-ACCESS read-only
			STATUS current
			DESCRIPTION
				"Description."
			::= { gponOnuMacAddressEntry 5 }

		
		-- 1.3.6.1.4.1.34592.1.5.1.1.2.18.12
		gponOnuWanConfigDataTable OBJECT-TYPE
			SYNTAX SEQUENCE OF GponOnuWanConfigDataEntry
			MAX-ACCESS not-accessible
			STATUS current
			DESCRIPTION
				"Description."
			::= { gponOnuObjects 12 }

		
		-- 1.3.6.1.4.1.34592.1.5.1.1.2.18.12.1
		gponOnuWanConfigDataEntry OBJECT-TYPE
			SYNTAX GponOnuWanConfigDataEntry
			MAX-ACCESS not-accessible
			STATUS current
			DESCRIPTION
				"Description."
			INDEX { gponOltDeviceId, gponOltCardId, gponOltPortId, gponOnuId, gponOnuWanInfoWanId
				 }
			::= { gponOnuWanConfigDataTable 1 }

		
		GponOnuWanConfigDataEntry ::=
			SEQUENCE { 
				gponOnuWanConfigDataConnectMode
					INTEGER,
				gponOnuWanConfigDataConnectType
					INTEGER,
				gponOnuWanConfigDataVlan
					Unsigned32,
				gponOnuWanConfigDataPriority
					Unsigned32,
				gponOnuWanConfigDataVlanMode
					INTEGER,
				gponOnuWanConfigDataIgmpProxy
					INTEGER,
				gponOnuWanConfigDataMvlan
					Unsigned32,
				gponOnuWanConfigDataMtu
					Unsigned32,
				gponOnuWanConfigDataDspMode
					INTEGER,
				gponOnuWanConfigDataPppoeUserName
					DisplayString,
				gponOnuWanConfigDataPppoePassword
					DisplayString,
				gponOnuWanConfigDataIpAddress
					IpAddress,
				gponOnuWanConfigDataIpNetmask
					IpAddress,
				gponOnuWanConfigDataIpGateway
					IpAddress,
				gponOnuWanConfigDataDns
					IpAddress,
				gponOnuWanConfigDataDns2
					IpAddress,
				gponOnuWanConfigDataBridgeMode
					INTEGER,
				gponOnuWanConfigDataRowStatus
					RowStatus,
				gponOnuWanConfigDataWanName
					OCTET STRING,
				gponOnuWanConfigDataVersion
					INTEGER,
				gponOnuWanConfigDataDscp
					Unsigned32,
				gponOnuWanConfigDataPppoeServiceName
					DisplayString,
				gponOnuWanConfigDataLinkStatus
					INTEGER,
				gponOnuWanConfigDataIpv6Address
					OCTET STRING,
				gponOnuWanConfigDataIpv6AddressPrefix
					Unsigned32,
				gponOnuWanConfigDataIpv6Gateway
					OCTET STRING,
				gponOnuWanConfigDataIpv6Dns
					OCTET STRING,
				gponOnuWanConfigDataIpv6Dns2
					OCTET STRING
			 }

		-- 1.3.6.1.4.1.34592.1.5.1.1.2.18.12.1.1
		gponOnuWanConfigDataConnectMode OBJECT-TYPE
			SYNTAX INTEGER
				{
				bridge(0),
				route(1)
				}
			MAX-ACCESS read-create
			STATUS current
			DESCRIPTION
				"Description."
			::= { gponOnuWanConfigDataEntry 1 }

		
		-- 1.3.6.1.4.1.34592.1.5.1.1.2.18.12.1.2
		gponOnuWanConfigDataConnectType OBJECT-TYPE
			SYNTAX INTEGER
				{
				tr069(0),
				internet(1),
				voice(2),
				other(3),
				voice-internet(4),
				tr069-internet(5),
				tr069-voice(6),
				tr069-voice-internet(7)
				}
			MAX-ACCESS read-create
			STATUS current
			DESCRIPTION
				"Description."
			::= { gponOnuWanConfigDataEntry 2 }

		
		-- 1.3.6.1.4.1.34592.1.5.1.1.2.18.12.1.3
		gponOnuWanConfigDataVlan OBJECT-TYPE
			SYNTAX Unsigned32 (1..4094)
			MAX-ACCESS read-create
			STATUS current
			DESCRIPTION
				"Description."
			::= { gponOnuWanConfigDataEntry 3 }

		
		-- 1.3.6.1.4.1.34592.1.5.1.1.2.18.12.1.4
		gponOnuWanConfigDataPriority OBJECT-TYPE
			SYNTAX Unsigned32 (0..7)
			MAX-ACCESS read-create
			STATUS current
			DESCRIPTION
				"Description."
			::= { gponOnuWanConfigDataEntry 4 }

		
		-- 1.3.6.1.4.1.34592.1.5.1.1.2.18.12.1.5
		gponOnuWanConfigDataVlanMode OBJECT-TYPE
			SYNTAX INTEGER
				{
				untag(0),
				transparent(1),
				tag(2)
				}
			MAX-ACCESS read-create
			STATUS current
			DESCRIPTION
				"Description."
			::= { gponOnuWanConfigDataEntry 5 }

		
		-- 1.3.6.1.4.1.34592.1.5.1.1.2.18.12.1.6
		gponOnuWanConfigDataIgmpProxy OBJECT-TYPE
			SYNTAX INTEGER
				{
				disable(0),
				enable(1)
				}
			MAX-ACCESS read-create
			STATUS current
			DESCRIPTION
				"Description."
			::= { gponOnuWanConfigDataEntry 6 }

		
		-- 1.3.6.1.4.1.34592.1.5.1.1.2.18.12.1.7
		gponOnuWanConfigDataMvlan OBJECT-TYPE
			SYNTAX Unsigned32 (1..4094)
			MAX-ACCESS read-create
			STATUS current
			DESCRIPTION
				"Description."
			::= { gponOnuWanConfigDataEntry 7 }

		
		-- 1.3.6.1.4.1.34592.1.5.1.1.2.18.12.1.8
		gponOnuWanConfigDataMtu OBJECT-TYPE
			SYNTAX Unsigned32 (576..1492)
			MAX-ACCESS read-create
			STATUS current
			DESCRIPTION
				"Description."
			::= { gponOnuWanConfigDataEntry 8 }

		
		-- 1.3.6.1.4.1.34592.1.5.1.1.2.18.12.1.9
		gponOnuWanConfigDataDspMode OBJECT-TYPE
			SYNTAX INTEGER
				{
				dhcp(0),
				static(1),
				pppoe(2),
				invalid(255)
				}
			MAX-ACCESS read-create
			STATUS current
			DESCRIPTION
				"0xFF: invalid value."
			::= { gponOnuWanConfigDataEntry 9 }

		
		-- 1.3.6.1.4.1.34592.1.5.1.1.2.18.12.1.10
		gponOnuWanConfigDataPppoeUserName OBJECT-TYPE
			SYNTAX DisplayString (SIZE (1..24))
			MAX-ACCESS read-create
			STATUS current
			DESCRIPTION
				"Description."
			::= { gponOnuWanConfigDataEntry 10 }

		
		-- 1.3.6.1.4.1.34592.1.5.1.1.2.18.12.1.11
		gponOnuWanConfigDataPppoePassword OBJECT-TYPE
			SYNTAX DisplayString (SIZE (1..24))
			MAX-ACCESS read-create
			STATUS current
			DESCRIPTION
				"Description."
			::= { gponOnuWanConfigDataEntry 11 }

		
		-- 1.3.6.1.4.1.34592.1.5.1.1.2.18.12.1.12
		gponOnuWanConfigDataIpAddress OBJECT-TYPE
			SYNTAX IpAddress
			MAX-ACCESS read-create
			STATUS current
			DESCRIPTION
				"Description."
			::= { gponOnuWanConfigDataEntry 12 }

		
		-- 1.3.6.1.4.1.34592.1.5.1.1.2.18.12.1.16
		gponOnuWanConfigDataIpNetmask OBJECT-TYPE
			SYNTAX IpAddress
			MAX-ACCESS read-create
			STATUS current
			DESCRIPTION
				"Description."
			::= { gponOnuWanConfigDataEntry 13 }

		
		-- 1.3.6.1.4.1.34592.1.5.1.1.2.18.12.1.17
		gponOnuWanConfigDataIpGateway OBJECT-TYPE
			SYNTAX IpAddress
			MAX-ACCESS read-create
			STATUS current
			DESCRIPTION
				"Description."
			::= { gponOnuWanConfigDataEntry 14 }

		
		-- 1.3.6.1.4.1.34592.1.5.1.1.2.18.12.1.18
		gponOnuWanConfigDataDns OBJECT-TYPE
			SYNTAX IpAddress
			MAX-ACCESS read-create
			STATUS current
			DESCRIPTION
				"Description."
			::= { gponOnuWanConfigDataEntry 15 }

		
		-- 1.3.6.1.4.1.34592.1.5.1.1.2.18.12.1.19
		gponOnuWanConfigDataDns2 OBJECT-TYPE
			SYNTAX IpAddress
			MAX-ACCESS read-create
			STATUS current
			DESCRIPTION
				"Description."
			::= { gponOnuWanConfigDataEntry 16 }

		
		-- 1.3.6.1.4.1.34592.1.5.1.1.2.18.12.1.20
		gponOnuWanConfigDataBridgeMode OBJECT-TYPE
			SYNTAX INTEGER
				{
				pppoe-bridge(0),
				ip-bridge(1)
				}
			MAX-ACCESS read-only
			STATUS current
			DESCRIPTION
				"Description."
			::= { gponOnuWanConfigDataEntry 17 }

		
		-- 1.3.6.1.4.1.34592.1.5.1.1.2.18.12.1.22
		gponOnuWanConfigDataRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { gponOnuWanConfigDataEntry 18 }

		
		-- 1.3.6.1.4.1.34592.1.5.1.1.2.18.12.1.19
		gponOnuWanConfigDataWanName OBJECT-TYPE
			SYNTAX OCTET STRING
			MAX-ACCESS read-create
			STATUS current
			DESCRIPTION
				"Description."
			::= { gponOnuWanConfigDataEntry 19 }

		
		-- 1.3.6.1.4.1.34592.1.5.1.1.2.18.12.1.20
		gponOnuWanConfigDataVersion OBJECT-TYPE
			SYNTAX INTEGER
				{
				IPv4(0),
				IPv6(1),
				IPv4-IPv6(2)
				}
			MAX-ACCESS read-create
			STATUS current
			DESCRIPTION
				"Description."
			::= { gponOnuWanConfigDataEntry 20 }

		
		-- 1.3.6.1.4.1.34592.1.5.1.1.2.18.12.1.21
		gponOnuWanConfigDataDscp OBJECT-TYPE
			SYNTAX Unsigned32 (0..63)
			MAX-ACCESS read-create
			STATUS current
			DESCRIPTION
				"Description."
			::= { gponOnuWanConfigDataEntry 21 }

		
		-- 1.3.6.1.4.1.34592.1.5.1.1.2.18.12.1.22
		gponOnuWanConfigDataPppoeServiceName OBJECT-TYPE
			SYNTAX DisplayString
			MAX-ACCESS read-create
			STATUS current
			DESCRIPTION
				"Description."
			::= { gponOnuWanConfigDataEntry 22 }

		
		-- 1.3.6.1.4.1.34592.1.5.1.1.2.18.12.1.23
		gponOnuWanConfigDataLinkStatus OBJECT-TYPE
			SYNTAX INTEGER
				{
				Down(0),
				Up(1)
				}
			MAX-ACCESS read-only
			STATUS current
			DESCRIPTION
				"Description."
			::= { gponOnuWanConfigDataEntry 23 }

		
		-- 1.3.6.1.4.1.34592.1.5.1.1.2.18.12.1.24
		gponOnuWanConfigDataIpv6Address OBJECT-TYPE
			SYNTAX OCTET STRING
			MAX-ACCESS read-create
			STATUS current
			DESCRIPTION
				"Description."
			::= { gponOnuWanConfigDataEntry 24 }

		
		-- 1.3.6.1.4.1.34592.1.5.1.1.2.18.12.1.25
		gponOnuWanConfigDataIpv6AddressPrefix OBJECT-TYPE
			SYNTAX Unsigned32
			MAX-ACCESS read-create
			STATUS current
			DESCRIPTION
				"Description."
			::= { gponOnuWanConfigDataEntry 25 }

		
		-- 1.3.6.1.4.1.34592.1.5.1.1.2.18.12.1.26
		gponOnuWanConfigDataIpv6Gateway OBJECT-TYPE
			SYNTAX OCTET STRING
			MAX-ACCESS read-create
			STATUS current
			DESCRIPTION
				"Description."
			::= { gponOnuWanConfigDataEntry 26 }

		
		-- 1.3.6.1.4.1.34592.1.5.1.1.2.18.12.1.27
		gponOnuWanConfigDataIpv6Dns OBJECT-TYPE
			SYNTAX OCTET STRING
			MAX-ACCESS read-create
			STATUS current
			DESCRIPTION
				"Description."
			::= { gponOnuWanConfigDataEntry 27 }

		
		-- 1.3.6.1.4.1.34592.1.5.1.1.2.18.12.1.28
		gponOnuWanConfigDataIpv6Dns2 OBJECT-TYPE
			SYNTAX OCTET STRING
			MAX-ACCESS read-create
			STATUS current
			DESCRIPTION
				"Description."
			::= { gponOnuWanConfigDataEntry 28 }

		
--  1.3.6.1.4.1.34592.1.5.1.1.2.18.13
		-- 1.3.6.1.4.1.34592.1.5.1.1.2.18.13
		onuAutoRebootTable OBJECT-TYPE
			SYNTAX SEQUENCE OF OnuAutoRebootEntry
			MAX-ACCESS not-accessible
			STATUS current
			DESCRIPTION
				"Description."
			::= { gponOnuObjects 13 }

		
		-- 1.3.6.1.4.1.34592.1.5.1.1.2.18.13.1
		onuAutoRebootEntry OBJECT-TYPE
			SYNTAX OnuAutoRebootEntry
			MAX-ACCESS not-accessible
			STATUS current
			DESCRIPTION
				"Description."
			INDEX { gponOltDeviceId, gponOltCardId, gponOltPortId, gponOnuId, gponOnuSuccess
				 }
			::= { onuAutoRebootTable 1 }

		
		OnuAutoRebootEntry ::=
			SEQUENCE { 
				onuAutoRebootAbsoluteTime
					OCTET STRING,
				onuAutoRebootRelativeTime
					OCTET STRING,
				onuAutoRebootInterval
					Integer32,
				onuAutoRebootRowStatus
					RowStatus
			 }

		-- 1.3.6.1.4.1.34592.1.5.1.1.2.18.13.1.1
		onuAutoRebootAbsoluteTime OBJECT-TYPE
			SYNTAX OCTET STRING
			MAX-ACCESS read-create
			STATUS current
			DESCRIPTION
				"Onu auto reboot absolute time. foxmat:YYYY/MM/DD-HH:MM:SS"
			::= { onuAutoRebootEntry 1 }

		
		-- 1.3.6.1.4.1.34592.1.5.1.1.2.18.13.1.2
		onuAutoRebootRelativeTime OBJECT-TYPE
			SYNTAX OCTET STRING
			MAX-ACCESS read-create
			STATUS current
			DESCRIPTION
				"Onu auto reboot relative time. uint:day"
			::= { onuAutoRebootEntry 2 }
			
		-- 1.3.6.1.4.1.34592.1.5.1.1.2.18.13.1.3
		onuAutoRebootInterval OBJECT-TYPE
			SYNTAX Integer32
			MAX-ACCESS read-create
			STATUS current
			DESCRIPTION
				"Description."
			::= { onuAutoRebootEntry 3 }

		
		-- 1.3.6.1.4.1.34592.1.5.1.1.2.18.13.1.4
		onuAutoRebootRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { onuAutoRebootEntry 4 }

		
--  1.3.6.1.4.1.34592.1.5.1.1.2.18.14
		gponOnuNumberTable OBJECT-TYPE
			SYNTAX SEQUENCE OF GponOnuNumberEntry
			MAX-ACCESS not-accessible
			STATUS current
			DESCRIPTION
				"Description."
			::= { gponOnuObjects 14 }

		
--  1.3.6.1.4.1.34592.1.5.1.1.2.18.14.1
		gponOnuNumberEntry OBJECT-TYPE
			SYNTAX GponOnuNumberEntry
			MAX-ACCESS not-accessible
			STATUS current
			DESCRIPTION
				"Description."
			INDEX { gponOltDeviceId, gponOltCardId, gponOltPortId }
			::= { gponOnuNumberTable 1 }

		
		GponOnuNumberEntry ::=
			SEQUENCE { 
				gponOnuTotal
					INTEGER,
				gponOnuSuccess
					INTEGER,
				gponOnuFail
					INTEGER,
				gponOnuOffline
					INTEGER
			 }

--  1.3.6.1.4.1.34592.1.5.1.1.2.18.14.1.1
		gponOnuTotal OBJECT-TYPE
			SYNTAX INTEGER
			MAX-ACCESS read-only
			STATUS current
			DESCRIPTION
				"Description."
			::= { gponOnuNumberEntry 1 }

		
--  1.3.6.1.4.1.34592.1.5.1.1.2.18.14.1.2
		gponOnuSuccess OBJECT-TYPE
			SYNTAX INTEGER
			MAX-ACCESS read-only
			STATUS current
			DESCRIPTION
				"Description."
			::= { gponOnuNumberEntry 2 }

		
--  1.3.6.1.4.1.34592.1.5.1.1.2.18.14.1.3
		gponOnuFail OBJECT-TYPE
			SYNTAX INTEGER
			MAX-ACCESS read-only
			STATUS current
			DESCRIPTION
				"Description."
			::= { gponOnuNumberEntry 3 }

		
--  1.3.6.1.4.1.34592.1.5.1.1.2.18.14.1.4
		gponOnuOffline OBJECT-TYPE
			SYNTAX INTEGER
			MAX-ACCESS read-only
			STATUS current
			DESCRIPTION
				"Description."
			::= { gponOnuNumberEntry 4 }

		
		-- 1.3.6.1.4.1.34592.1.5.1.1.2.18.15
		gponOnuWhiteTable OBJECT-TYPE
			SYNTAX SEQUENCE OF GponOnuWhiteEntry
			MAX-ACCESS not-accessible
			STATUS current
			DESCRIPTION
				"Description."
			::= { gponOnuObjects 15 }

		
		-- 1.3.6.1.4.1.34592.1.5.1.1.2.18.15.1
		gponOnuWhiteEntry OBJECT-TYPE
			SYNTAX GponOnuWhiteEntry
			MAX-ACCESS not-accessible
			STATUS current
			DESCRIPTION
				"Description."
			INDEX { gponOnuWhiteTableIndex }
			::= { gponOnuWhiteTable 1 }

		
		GponOnuWhiteEntry ::=
			SEQUENCE { 
				gponOnuWhiteTableIndex
					Integer32,
				gponOnuWihteTableStartSn
					DisplayString,
				gponOnuWihteTableEndSn
					DisplayString,
				gponOnuWhiteTableRowStatus
					RowStatus,
				gponOnuWhiteTableClear
					INTEGER
			 }

		-- 1.3.6.1.4.1.34592.1.5.1.1.2.18.15.1.1
		gponOnuWhiteTableIndex OBJECT-TYPE
			SYNTAX Integer32
			MAX-ACCESS not-accessible
			STATUS current
			DESCRIPTION
				"Description."
			::= { gponOnuWhiteEntry 1 }

		
		-- 1.3.6.1.4.1.34592.1.5.1.1.2.18.15.1.2
		gponOnuWihteTableStartSn OBJECT-TYPE
			SYNTAX DisplayString
			MAX-ACCESS read-create
			STATUS current
			DESCRIPTION
				"Description."
			::= { gponOnuWhiteEntry 2 }

		
		-- 1.3.6.1.4.1.34592.1.5.1.1.2.18.15.1.3
		gponOnuWihteTableEndSn OBJECT-TYPE
			SYNTAX DisplayString
			MAX-ACCESS read-create
			STATUS current
			DESCRIPTION
				"Description."
			::= { gponOnuWhiteEntry 3 }

		
		-- 1.3.6.1.4.1.34592.1.5.1.1.2.18.15.1.4
		gponOnuWhiteTableRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { gponOnuWhiteEntry 4 }

		
		-- 1.3.6.1.4.1.34592.1.5.1.1.2.18.15.1.5
		gponOnuWhiteTableClear OBJECT-TYPE
			SYNTAX INTEGER
			MAX-ACCESS read-write
			STATUS current
			DESCRIPTION
				"Description."
			::= { gponOnuWhiteEntry 5 }

		
		-- 1.3.6.1.4.1.34592.1.5.1.1.2.18.16
		gponRogueOnuInfoTable OBJECT-TYPE
			SYNTAX SEQUENCE OF GponRogueOnuInfoEntry
			MAX-ACCESS not-accessible
			STATUS current
			DESCRIPTION
				"Description."
			::= { gponOnuObjects 16 }

		
		-- 1.3.6.1.4.1.34592.1.5.1.1.2.18.16.1
		gponRogueOnuInfoEntry OBJECT-TYPE
			SYNTAX GponRogueOnuInfoEntry
			MAX-ACCESS not-accessible
			STATUS current
			DESCRIPTION
				"Description."
			INDEX { gponOltDeviceId, gponOltCardId, gponOltPortId, gponOnuId }
			::= { gponRogueOnuInfoTable 1 }

		
		GponRogueOnuInfoEntry ::=
			SEQUENCE { 
				gponRogueOnuInfoTableOnuSn
					DisplayString,
				gponRogueOnuReEnable
					INTEGER
			 }

		-- 1.3.6.1.4.1.34592.1.5.1.1.2.18.16.1.1
		gponRogueOnuInfoTableOnuSn OBJECT-TYPE
			SYNTAX DisplayString
			MAX-ACCESS read-only
			STATUS current
			DESCRIPTION
				"Description."
			::= { gponRogueOnuInfoEntry 1 }

		
		-- 1.3.6.1.4.1.34592.1.5.1.1.2.18.16.1.2
		gponRogueOnuReEnable OBJECT-TYPE
			SYNTAX INTEGER
			MAX-ACCESS read-write
			STATUS current
			DESCRIPTION
				"Description."
			::= { gponRogueOnuInfoEntry 2 }

		
		-- 1.3.6.1.4.1.34592.1.5.1.1.2.18.17
		gponOnuAutoUpdateSelectTable OBJECT-TYPE
			SYNTAX SEQUENCE OF GponOnuAutoUpdateSelectEntry
			MAX-ACCESS not-accessible
			STATUS current
			DESCRIPTION
				"Description."
			::= { gponOnuObjects 17 }

		
		-- 1.3.6.1.4.1.34592.1.5.1.1.2.18.17.1
		gponOnuAutoUpdateSelectEntry OBJECT-TYPE
			SYNTAX GponOnuAutoUpdateSelectEntry
			MAX-ACCESS not-accessible
			STATUS current
			DESCRIPTION
				"Description."
			INDEX { gponOnuType, gponOnuAutoUpdateTableIndex }
			::= { gponOnuAutoUpdateSelectTable 1 }

		
		GponOnuAutoUpdateSelectEntry ::=
			SEQUENCE { 
				gponOnuAutoUpdateSelectType
					INTEGER,
				gponOnuAutoUpdateSelectPortId
					Integer32,
				gponOnuAutoUpdateSelectOnuIdList
					DisplayString,
				gponOnuAutoUpdateSelectMatchVersion
					DisplayString,
				gponOnuAutoUpdateSelectMatchVendor
					DisplayString,
				gponOnuAutoUpdateSelectMatchEquipId
					DisplayString
			 }

		-- 1.3.6.1.4.1.34592.1.5.1.1.2.18.17.1.1
		gponOnuAutoUpdateSelectType OBJECT-TYPE
			SYNTAX INTEGER
				{
				default(1),
				ont-base(2),
				port-base(3)
				}
			MAX-ACCESS read-write
			STATUS current
			DESCRIPTION
				"Description."
			::= { gponOnuAutoUpdateSelectEntry 1 }

		
		-- 1.3.6.1.4.1.34592.1.5.1.1.2.18.17.1.2
		gponOnuAutoUpdateSelectPortId OBJECT-TYPE
			SYNTAX Integer32
			MAX-ACCESS read-write
			STATUS current
			DESCRIPTION
				"Description."
			::= { gponOnuAutoUpdateSelectEntry 2 }

		
		-- 1.3.6.1.4.1.34592.1.5.1.1.2.18.17.1.3
		gponOnuAutoUpdateSelectOnuIdList OBJECT-TYPE
			SYNTAX DisplayString
			MAX-ACCESS read-write
			STATUS current
			DESCRIPTION
				"Description."
			::= { gponOnuAutoUpdateSelectEntry 3 }

		
		-- 1.3.6.1.4.1.34592.1.5.1.1.2.18.17.1.4
		gponOnuAutoUpdateSelectMatchVersion OBJECT-TYPE
			SYNTAX DisplayString (SIZE (1..14))
			MAX-ACCESS read-write
			STATUS current
			DESCRIPTION
				"Description."
			::= { gponOnuAutoUpdateSelectEntry 4 }

		
		-- 1.3.6.1.4.1.34592.1.5.1.1.2.18.17.1.5
		gponOnuAutoUpdateSelectMatchVendor OBJECT-TYPE
			SYNTAX DisplayString (SIZE (4))
			MAX-ACCESS read-write
			STATUS current
			DESCRIPTION
				"Description."
			::= { gponOnuAutoUpdateSelectEntry 5 }

		
		-- 1.3.6.1.4.1.34592.1.5.1.1.2.18.17.1.6
		gponOnuAutoUpdateSelectMatchEquipId OBJECT-TYPE
			SYNTAX DisplayString
			MAX-ACCESS read-write
			STATUS current
			DESCRIPTION
				"Description."
			::= { gponOnuAutoUpdateSelectEntry 6 }

		
		-- 1.3.6.1.4.1.34592.1.5.1.1.2.18.18
		gponOnuAutoUpdateObject OBJECT IDENTIFIER ::= { gponOnuObjects 18 }

		
		-- 1.3.6.1.4.1.34592.1.5.1.1.2.18.18.1
		gponOnuAutoUpdateConfigTable OBJECT-TYPE
			SYNTAX SEQUENCE OF GponOnuAutoUpdateConfigEntry
			MAX-ACCESS not-accessible
			STATUS current
			DESCRIPTION
				"Description."
			::= { gponOnuAutoUpdateObject 1 }

		
		-- 1.3.6.1.4.1.34592.1.5.1.1.2.18.18.1.1
		gponOnuAutoUpdateConfigEntry OBJECT-TYPE
			SYNTAX GponOnuAutoUpdateConfigEntry
			MAX-ACCESS not-accessible
			STATUS current
			DESCRIPTION
				"Description."
			INDEX { gponOnuAutoUpdateTableIndex }
			::= { gponOnuAutoUpdateConfigTable 1 }

		
		GponOnuAutoUpdateConfigEntry ::=
			SEQUENCE { 
				gponOnuAutoUpdateTableIndex
					Integer32,
				gponOnuAutoUpdateTableStatus
					INTEGER,
				gponOnuAutoUpdateTableMode
					INTEGER
			 }

		-- 1.3.6.1.4.1.34592.1.5.1.1.2.18.18.1.1.1
		gponOnuAutoUpdateTableIndex OBJECT-TYPE
			SYNTAX Integer32
			MAX-ACCESS not-accessible
			STATUS current
			DESCRIPTION
				"Description."
			::= { gponOnuAutoUpdateConfigEntry 1 }

		
		-- 1.3.6.1.4.1.34592.1.5.1.1.2.18.18.1.1.2
		gponOnuAutoUpdateTableStatus OBJECT-TYPE
			SYNTAX INTEGER
				{
				disable(0),
				enable(1)
				}
			MAX-ACCESS read-write
			STATUS current
			DESCRIPTION
				"Description."
			::= { gponOnuAutoUpdateConfigEntry 2 }

		
		-- 1.3.6.1.4.1.34592.1.5.1.1.2.18.18.1.1.3
		gponOnuAutoUpdateTableMode OBJECT-TYPE
			SYNTAX INTEGER
				{
				timer(1),
				online-update(2),
				both(3)
				}
			MAX-ACCESS read-write
			STATUS current
			DESCRIPTION
				"Description."
			::= { gponOnuAutoUpdateConfigEntry 3 }

		
		-- 1.3.6.1.4.1.34592.1.5.1.1.2.18.18.2
		gponOnuAutoUpdateTaskTable OBJECT-TYPE
			SYNTAX SEQUENCE OF GponOnuAutoUpdateTaskEntry
			MAX-ACCESS not-accessible
			STATUS current
			DESCRIPTION
				"Description."
			::= { gponOnuAutoUpdateObject 2 }

		
		-- 1.3.6.1.4.1.34592.1.5.1.1.2.18.18.2.1
		gponOnuAutoUpdateTaskEntry OBJECT-TYPE
			SYNTAX GponOnuAutoUpdateTaskEntry
			MAX-ACCESS not-accessible
			STATUS current
			DESCRIPTION
				"Description."
			INDEX { gponOnuAutoUpdateTaskIndex }
			::= { gponOnuAutoUpdateTaskTable 1 }

		
		GponOnuAutoUpdateTaskEntry ::=
			SEQUENCE { 
				gponOnuAutoUpdateTaskIndex
					Integer32,
				gponOnuAutoUpdateTaskOnuImage
					DisplayString,
				gponOnuAutoUpdateTaskVersion
					DisplayString,
				gponOnuAutoUpdateTaskTriggerTime
					DisplayString,
				gponOnuAutoUpdateTaskMatchVendor
					DisplayString,
				gponOnuAutoUpdateTaskMatchEquipId
					DisplayString
			 }

		-- 1.3.6.1.4.1.34592.1.5.1.1.2.18.18.2.1.1
		gponOnuAutoUpdateTaskIndex OBJECT-TYPE
			SYNTAX Integer32
			MAX-ACCESS not-accessible
			STATUS current
			DESCRIPTION
				"Description."
			::= { gponOnuAutoUpdateTaskEntry 1 }

		
		-- 1.3.6.1.4.1.34592.1.5.1.1.2.18.18.2.1.2
		gponOnuAutoUpdateTaskOnuImage OBJECT-TYPE
			SYNTAX DisplayString (SIZE (1..80))
			MAX-ACCESS read-write
			STATUS current
			DESCRIPTION
				"Description."
			::= { gponOnuAutoUpdateTaskEntry 2 }

		
		-- 1.3.6.1.4.1.34592.1.5.1.1.2.18.18.2.1.3
		gponOnuAutoUpdateTaskVersion OBJECT-TYPE
			SYNTAX DisplayString (SIZE (1..14))
			MAX-ACCESS read-write
			STATUS current
			DESCRIPTION
				"Description."
			::= { gponOnuAutoUpdateTaskEntry 3 }

		
		-- 1.3.6.1.4.1.34592.1.5.1.1.2.18.18.2.1.4
		gponOnuAutoUpdateTaskTriggerTime OBJECT-TYPE
			SYNTAX DisplayString
			MAX-ACCESS read-write
			STATUS current
			DESCRIPTION
				"input foxmat:YYYY/MM/DD-HH:MM:SS"
			::= { gponOnuAutoUpdateTaskEntry 4 }

		
		-- 1.3.6.1.4.1.34592.1.5.1.1.2.18.18.2.1.5
		gponOnuAutoUpdateTaskMatchVendor OBJECT-TYPE
			SYNTAX DisplayString (SIZE (4))
			MAX-ACCESS read-write
			STATUS current
			DESCRIPTION
				"Description."
			::= { gponOnuAutoUpdateTaskEntry 5 }

		
		-- 1.3.6.1.4.1.34592.1.5.1.1.2.18.18.2.1.6
		gponOnuAutoUpdateTaskMatchEquipId OBJECT-TYPE
			SYNTAX DisplayString (SIZE (1..20))
			MAX-ACCESS read-write
			STATUS current
			DESCRIPTION
				"Description."
			::= { gponOnuAutoUpdateTaskEntry 6 }

		
		-- 1.3.6.1.4.1.34592.1.5.1.1.2.18.19
		gponOnuOpticalCollectTable OBJECT-TYPE
			SYNTAX SEQUENCE OF GponOnuOpticalCollectEntry
			MAX-ACCESS not-accessible
			STATUS current
			DESCRIPTION
				"Description."
			::= { gponOnuObjects 19 }

		
		-- 1.3.6.1.4.1.34592.1.5.1.1.2.18.19.1
		gponOnuOpticalCollectEntry OBJECT-TYPE
			SYNTAX GponOnuOpticalCollectEntry
			MAX-ACCESS not-accessible
			STATUS current
			DESCRIPTION
				"Description."
			INDEX { gponOltPortId, gponOnuOpticalCollectIndex }
			::= { gponOnuOpticalCollectTable 1 }

		
		GponOnuOpticalCollectEntry ::=
			SEQUENCE { 
				gponOnuOpticalCollectIndex
					Integer32,
				gponOnuOpticalCollectInformate
					OCTET STRING
			 }

		-- 1.3.6.1.4.1.34592.1.5.1.1.2.18.19.1.1
		gponOnuOpticalCollectIndex OBJECT-TYPE
			SYNTAX Integer32
			MAX-ACCESS not-accessible
			STATUS current
			DESCRIPTION
				"Description."
			::= { gponOnuOpticalCollectEntry 1 }

		
		-- 1.3.6.1.4.1.34592.1.5.1.1.2.18.19.1.2
		gponOnuOpticalCollectInformate OBJECT-TYPE
			SYNTAX OCTET STRING
			MAX-ACCESS read-only
			STATUS current
			DESCRIPTION
				"Description."
			::= { gponOnuOpticalCollectEntry 2 }

		
		-- 1.3.6.1.4.1.34592.1.5.1.1.2.18.20
		gponOnuAutoFindCollectTable OBJECT-TYPE
			SYNTAX SEQUENCE OF GponOnuAutoFindCollectEntry
			MAX-ACCESS not-accessible
			STATUS current
			DESCRIPTION
				"Description."
			::= { gponOnuObjects 20 }

		
		-- 1.3.6.1.4.1.34592.1.5.1.1.2.18.20.1
		gponOnuAutoFindCollectEntry OBJECT-TYPE
			SYNTAX GponOnuAutoFindCollectEntry
			MAX-ACCESS not-accessible
			STATUS current
			DESCRIPTION
				"Description."
			INDEX { gponOnuAutoFindCollectIndex }
			::= { gponOnuAutoFindCollectTable 1 }

		
		GponOnuAutoFindCollectEntry ::=
			SEQUENCE { 
				gponOnuAutoFindCollectIndex
					Integer32,
				gponOnuAutoFindCollectInformate
					OCTET STRING
			 }

		-- 1.3.6.1.4.1.34592.1.5.1.1.2.18.20.1.1
		gponOnuAutoFindCollectIndex OBJECT-TYPE
			SYNTAX Integer32
			MAX-ACCESS not-accessible
			STATUS current
			DESCRIPTION
				"Description."
			::= { gponOnuAutoFindCollectEntry 1 }

		
		-- 1.3.6.1.4.1.34592.1.5.1.1.2.18.20.1.2
		gponOnuAutoFindCollectInformate OBJECT-TYPE
			SYNTAX OCTET STRING
			MAX-ACCESS read-only
			STATUS current
			DESCRIPTION
				"Description."
			::= { gponOnuAutoFindCollectEntry 2 }

		
		-- 1.3.6.1.4.1.34592.1.5.1.1.2.18.21
		gponOnuWifiCommonTable OBJECT-TYPE
			SYNTAX SEQUENCE OF GponOnuWifiCommonEntry
			MAX-ACCESS not-accessible
			STATUS current
			DESCRIPTION
				"Description."
			::= { gponOnuObjects 21 }

		
		-- 1.3.6.1.4.1.34592.1.5.1.1.2.18.21.1
		gponOnuWifiCommonEntry OBJECT-TYPE
			SYNTAX GponOnuWifiCommonEntry
			MAX-ACCESS not-accessible
			STATUS current
			DESCRIPTION
				"Description."
			INDEX { gponOltDeviceId, gponOltCardId, gponOltPortId, gponOnuId, gponOnuWifiFrequencyBand
				 }
			::= { gponOnuWifiCommonTable 1 }

		
		GponOnuWifiCommonEntry ::=
			SEQUENCE { 
				gponOnuWifiEnable
					INTEGER,
				gponOnuWifiMode
					INTEGER,
				gponOnuWifiBandwidth
					INTEGER,
				gponOnuWifiChannel
					INTEGER,
				gponOnuWifiPower
					INTEGER,
				gponOnuWifiCountryCode
					INTEGER,
				gponOnuWifiSgiEnable
					INTEGER,
				gponOnuWifiWpsEnable
					INTEGER,
				gponOnuWifiApIso
					INTEGER,
				gponOnuWifiCommonRowStatus
					RowStatus
			 }

		-- 1.3.6.1.4.1.34592.1.5.1.1.2.18.21.1.1
		gponOnuWifiEnable OBJECT-TYPE
			SYNTAX INTEGER
				{
				disable(0),
				enable(1)
				}
			MAX-ACCESS read-create
			STATUS current
			DESCRIPTION
				"Description."
			::= { gponOnuWifiCommonEntry 1 }

		
		-- 1.3.6.1.4.1.34592.1.5.1.1.2.18.21.1.2
		gponOnuWifiMode OBJECT-TYPE
			SYNTAX INTEGER
				{
				fb802-11b(0),
				fb802-11g(1),
				fb802-11b-g(2),
				fb802-11n(3),
				fb802-11b-g-n(4),
				fb802-11a(5),
				fb802-11a-n(6),
				fb802-11ac-a-n(7)
				}
			MAX-ACCESS read-create
			STATUS current
			DESCRIPTION
				"Description."
			::= { gponOnuWifiCommonEntry 2 }

		
		-- 1.3.6.1.4.1.34592.1.5.1.1.2.18.21.1.3
		gponOnuWifiBandwidth OBJECT-TYPE
			SYNTAX INTEGER
				{
				BD20MHz(0),
				BD40MHz(1),
				BD20-40MHz(2),
				BD20-40-80MHz(3)
				}
			MAX-ACCESS read-create
			STATUS current
			DESCRIPTION
				"Description."
			::= { gponOnuWifiCommonEntry 3 }

		
		-- 1.3.6.1.4.1.34592.1.5.1.1.2.18.21.1.4
		gponOnuWifiChannel OBJECT-TYPE
			SYNTAX INTEGER (0..161)
			MAX-ACCESS read-create
			STATUS current
			DESCRIPTION
				"Description."
			::= { gponOnuWifiCommonEntry 4 }

		
		-- 1.3.6.1.4.1.34592.1.5.1.1.2.18.21.1.5
		gponOnuWifiPower OBJECT-TYPE
			SYNTAX INTEGER
				{
				P100(0),
				P70(1),
				P50(2),
				P35(3),
				P15(4)
				}
			MAX-ACCESS read-create
			STATUS current
			DESCRIPTION
				"Description."
			::= { gponOnuWifiCommonEntry 5 }

		
		-- 1.3.6.1.4.1.34592.1.5.1.1.2.18.21.1.6
		gponOnuWifiCountryCode OBJECT-TYPE
			SYNTAX INTEGER
				{
				USA(0),
				India(1),
				European-Union(2),
				Spain(3),
				France(4),
				Japan(5),
				Israli(6),
				China-TaiWan(7),
				Russian(8),
				China(9),
				Global(10),
				WORLD-WIDE(11)
				}
			MAX-ACCESS read-create
			STATUS current
			DESCRIPTION
				"Description."
			::= { gponOnuWifiCommonEntry 6 }

		
		-- 1.3.6.1.4.1.34592.1.5.1.1.2.18.21.1.7
		gponOnuWifiSgiEnable OBJECT-TYPE
			SYNTAX INTEGER
				{
				disable(0),
				enable(1)
				}
			MAX-ACCESS read-create
			STATUS current
			DESCRIPTION
				"Description."
			::= { gponOnuWifiCommonEntry 7 }

		
		-- 1.3.6.1.4.1.34592.1.5.1.1.2.18.21.1.8
		gponOnuWifiWpsEnable OBJECT-TYPE
			SYNTAX INTEGER
				{
				disable(0),
				enable(1)
				}
			MAX-ACCESS read-create
			STATUS current
			DESCRIPTION
				"Description."
			::= { gponOnuWifiCommonEntry 8 }

		
		-- 1.3.6.1.4.1.34592.1.5.1.1.2.18.21.1.9
		gponOnuWifiApIso OBJECT-TYPE
			SYNTAX INTEGER
				{
				disable(0),
				enable(1)
				}
			MAX-ACCESS read-create
			STATUS current
			DESCRIPTION
				"Description."
			::= { gponOnuWifiCommonEntry 9 }

		
		-- 1.3.6.1.4.1.34592.1.5.1.1.2.18.21.1.10
		gponOnuWifiCommonRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { gponOnuWifiCommonEntry 10 }

		
		-- 1.3.6.1.4.1.34592.1.5.1.1.2.18.22
		gponOnuWifiSsidTable OBJECT-TYPE
			SYNTAX SEQUENCE OF GponOnuWifiSsidEntry
			MAX-ACCESS not-accessible
			STATUS current
			DESCRIPTION
				"Description."
			::= { gponOnuObjects 22 }

		
		-- 1.3.6.1.4.1.34592.1.5.1.1.2.18.22.1
		gponOnuWifiSsidEntry OBJECT-TYPE
			SYNTAX GponOnuWifiSsidEntry
			MAX-ACCESS not-accessible
			STATUS current
			DESCRIPTION
				"Description."
			INDEX { gponOltDeviceId, gponOltCardId, gponOltPortId, gponOnuId, gponOnuWifiSsid, 
				gponOnuWifiFrequencyBand }
			::= { gponOnuWifiSsidTable 1 }

		
		GponOnuWifiSsidEntry ::=
			SEQUENCE { 
				gponOnuWifiSsid
					Integer32,
				gponOnuWifiFrequencyBand
					Integer32,
				gponOnuWifiSsidStatus
					INTEGER,
				gponOnuWifiBroadcastCancel
					INTEGER,
				gponOnuWifiSsidName
					OCTET STRING,
				gponOnuWifiEncryptMode
					INTEGER,
				gponOnuWifiWpaEncrypt
					INTEGER,
				gponOnuWifiEncryptKey
					OCTET STRING,
				gponOnuWifiSsidMaxUser
					Integer32,
				gponOnuWifiSsidRowStatus
					RowStatus
			 }

		-- 1.3.6.1.4.1.34592.1.5.1.1.2.18.22.1.1
		gponOnuWifiSsid OBJECT-TYPE
			SYNTAX Integer32
			MAX-ACCESS not-accessible
			STATUS current
			DESCRIPTION
				"Description."
			::= { gponOnuWifiSsidEntry 1 }

		
		-- 1.3.6.1.4.1.34592.1.5.1.1.2.18.22.1.2
		gponOnuWifiFrequencyBand OBJECT-TYPE
			SYNTAX Integer32
			MAX-ACCESS not-accessible
			STATUS current
			DESCRIPTION
				"Description."
			::= { gponOnuWifiSsidEntry 2 }

		
		-- 1.3.6.1.4.1.34592.1.5.1.1.2.18.22.1.3
		gponOnuWifiSsidStatus OBJECT-TYPE
			SYNTAX INTEGER
				{
				disable(0),
				enable(1)
				}
			MAX-ACCESS read-create
			STATUS current
			DESCRIPTION
				"Description."
			::= { gponOnuWifiSsidEntry 3 }

		
		-- 1.3.6.1.4.1.34592.1.5.1.1.2.18.22.1.4
		gponOnuWifiBroadcastCancel OBJECT-TYPE
			SYNTAX INTEGER
				{
				disable(0),
				enable(1)
				}
			MAX-ACCESS read-create
			STATUS current
			DESCRIPTION
				"Description."
			::= { gponOnuWifiSsidEntry 4 }

		
		-- 1.3.6.1.4.1.34592.1.5.1.1.2.18.22.1.5
		gponOnuWifiSsidName OBJECT-TYPE
			SYNTAX OCTET STRING
			MAX-ACCESS read-create
			STATUS current
			DESCRIPTION
				"Description."
			::= { gponOnuWifiSsidEntry 5 }

		
		-- 1.3.6.1.4.1.34592.1.5.1.1.2.18.22.1.6
		gponOnuWifiEncryptMode OBJECT-TYPE
			SYNTAX INTEGER
				{
				open(0),
				wep(1),
				wpapsk(2),
				wpa2psk(3),
				wpa2psk-wpapsk(4),
				wep64bits(5),
				wep128bits(6)
				}
			MAX-ACCESS read-create
			STATUS current
			DESCRIPTION
				"Description."
			::= { gponOnuWifiSsidEntry 6 }

		
		-- 1.3.6.1.4.1.34592.1.5.1.1.2.18.22.1.7
		gponOnuWifiWpaEncrypt OBJECT-TYPE
			SYNTAX INTEGER
				{
				TKIP(0),
				AES(1),
				TKIPANDAES(2)
				}
			MAX-ACCESS read-create
			STATUS current
			DESCRIPTION
				"Description."
			::= { gponOnuWifiSsidEntry 7 }

		
		-- 1.3.6.1.4.1.34592.1.5.1.1.2.18.22.1.8
		gponOnuWifiEncryptKey OBJECT-TYPE
			SYNTAX OCTET STRING
			MAX-ACCESS read-create
			STATUS current
			DESCRIPTION
				"Description."
			::= { gponOnuWifiSsidEntry 8 }

		
		-- 1.3.6.1.4.1.34592.1.5.1.1.2.18.22.1.9
		gponOnuWifiSsidMaxUser OBJECT-TYPE
			SYNTAX Integer32 (0..128)
			MAX-ACCESS read-create
			STATUS current
			DESCRIPTION
				"Description."
			::= { gponOnuWifiSsidEntry 9 }

		
		-- 1.3.6.1.4.1.34592.1.5.1.1.2.18.22.1.10
		gponOnuWifiSsidRowStatus OBJECT-TYPE
			SYNTAX RowStatus
				{
				active(1),
				notInService(2),
				notReady(3),
				createAndGo(4),
				createAndWait(5),
				destroy(6)
				}
			MAX-ACCESS read-create
			STATUS current
			DESCRIPTION
				"Description."
			::= { gponOnuWifiSsidEntry 10 }

		
		-- 1.3.6.1.4.1.34592.1.5.1.1.2.18.23
		gponOnuWanConfigDataModifyTable OBJECT-TYPE
			SYNTAX SEQUENCE OF GponOnuWanConfigDataModifyEntry
			MAX-ACCESS not-accessible
			STATUS current
			DESCRIPTION
				"Description."
			::= { gponOnuObjects 23 }

		
		-- 1.3.6.1.4.1.34592.1.5.1.1.2.18.23.1
		gponOnuWanConfigDataModifyEntry OBJECT-TYPE
			SYNTAX GponOnuWanConfigDataModifyEntry
			MAX-ACCESS not-accessible
			STATUS current
			DESCRIPTION
				"Description."
			INDEX { gponOltDeviceId, gponOltCardId, gponOltPortId, gponOnuId, gponOnuWanInfoWanId
				 }
			::= { gponOnuWanConfigDataModifyTable 1 }

		
		GponOnuWanConfigDataModifyEntry ::=
			SEQUENCE { 
				gponOnuWanModifyDataBindLanMask
					BITS,
				gponOnuWanModifyDataBindSsidMask
					BITS,
				gponOnuWanModifyDataBindSsid5gMask
					BITS,
				gponOnuWanModifyDataAdminStatus
					INTEGER,
				gponOnuWanModifyDataNATstatus
					INTEGER,
				gponOnuWanModifyDataLANDHCPstatus
					INTEGER,
				gponOnuWanModifyDataDSCPstatus
					INTEGER,
				gponOnuWanModifyDataAutomaticallyGetIpv6Address
					INTEGER,
				gponOnuWanModifyDataDhcpv6PrefixDelegation
					INTEGER,
				gponOnuWanModifyDataAutomaticallyGetDnsv6Address
					INTEGER,
				gponOnuWanModifyDataOptionStatus
					INTEGER,
				gponOnuWanModifyDataOption60Part1
					OCTET STRING,
				gponOnuWanModifyDataOption60Part2
					OCTET STRING,
				gponOnuWanModifyDataSync
					INTEGER
			 }

--  1.3.6.1.4.1.34592.1.5.1.1.2.18.12.1.12
		-- 1.3.6.1.4.1.34592.1.5.1.1.2.18.23.1.1
		gponOnuWanModifyDataBindLanMask OBJECT-TYPE
			SYNTAX BITS
				{
				Lan1(0),
				Lan2(1),
				Lan3(2),
				Lan4(3),
				Lan5(4),
				Lan6(5),
				Lan7(6),
				Lan8(7)
				}
			MAX-ACCESS read-write
			STATUS current
			DESCRIPTION
				"LAN1:0x01 (1:bind 0:unbind)
				LAN2:0x02
				LAN3:0x04
				LAN4:0x08  etc...
				"
			::= { gponOnuWanConfigDataModifyEntry 1 }

		
--  1.3.6.1.4.1.34592.1.5.1.1.2.18.12.1.13
		-- 1.3.6.1.4.1.34592.1.5.1.1.2.18.23.1.2
		gponOnuWanModifyDataBindSsidMask OBJECT-TYPE
			SYNTAX BITS
				{
				ssid1(0),
				ssid2(1),
				ssid3(2),
				ssid4(3),
				ssid5(4),
				ssid6(5),
				ssid7(6),
				ssid8(7)
				}
			MAX-ACCESS read-write
			STATUS current
			DESCRIPTION
				"ssid1:0x01 (1:bind 0:unbind)
				ssid2:0x02
				ssid3:0x04
				ssid4:0x08  etc...
				"
			::= { gponOnuWanConfigDataModifyEntry 2 }

		
--  1.3.6.1.4.1.34592.1.5.1.1.2.18.12.1.14
		-- 1.3.6.1.4.1.34592.1.5.1.1.2.18.23.1.3
		gponOnuWanModifyDataBindSsid5gMask OBJECT-TYPE
			SYNTAX BITS
				{
				ssid5g-1(0),
				ssid5g-2(1),
				ssid5g-3(2),
				ssid5g-4(3),
				ssid5g-5(4),
				ssid5g-6(5),
				ssid5g-7(6),
				ssid5g-8(7)
				}
			MAX-ACCESS read-write
			STATUS current
			DESCRIPTION
				"5gssid1:0x01 (1:bind 0:unbind)
				5gssid1:0x02
				5gssid1:0x04
				5gssid1:0x08  etc...
				"
			::= { gponOnuWanConfigDataModifyEntry 3 }

		
--  1.3.6.1.4.1.34592.1.5.1.1.2.18.12.1.21
		-- 1.3.6.1.4.1.34592.1.5.1.1.2.18.23.1.4
		gponOnuWanModifyDataAdminStatus OBJECT-TYPE
			SYNTAX INTEGER
				{
				disable(0),
				enable(1)
				}
			MAX-ACCESS read-write
			STATUS current
			DESCRIPTION
				"Description."
			::= { gponOnuWanConfigDataModifyEntry 4 }

		
		-- 1.3.6.1.4.1.34592.1.5.1.1.2.18.23.1.5
		gponOnuWanModifyDataNATstatus OBJECT-TYPE
			SYNTAX INTEGER
				{
				Disable(0),
				Enable(1)
				}
			MAX-ACCESS read-write
			STATUS current
			DESCRIPTION
				"Description."
			::= { gponOnuWanConfigDataModifyEntry 5 }

		
		-- 1.3.6.1.4.1.34592.1.5.1.1.2.18.23.1.6
		gponOnuWanModifyDataLANDHCPstatus OBJECT-TYPE
			SYNTAX INTEGER
				{
				Disable(0),
				Enable(1)
				}
			MAX-ACCESS read-write
			STATUS current
			DESCRIPTION
				"Description."
			::= { gponOnuWanConfigDataModifyEntry 6 }

		
		-- 1.3.6.1.4.1.34592.1.5.1.1.2.18.23.1.7
		gponOnuWanModifyDataDSCPstatus OBJECT-TYPE
			SYNTAX INTEGER
				{
				Disable(0),
				Enable(1)
				}
			MAX-ACCESS read-write
			STATUS current
			DESCRIPTION
				"Description."
			::= { gponOnuWanConfigDataModifyEntry 7 }

		
		-- 1.3.6.1.4.1.34592.1.5.1.1.2.18.23.1.8
		gponOnuWanModifyDataAutomaticallyGetIpv6Address OBJECT-TYPE
			SYNTAX INTEGER
				{
				SLAAC(0),
				DHCP(1)
				}
			MAX-ACCESS read-write
			STATUS current
			DESCRIPTION
				"Description."
			::= { gponOnuWanConfigDataModifyEntry 8 }

		
		-- 1.3.6.1.4.1.34592.1.5.1.1.2.18.23.1.9
		gponOnuWanModifyDataDhcpv6PrefixDelegation OBJECT-TYPE
			SYNTAX INTEGER
				{
				Disable(0),
				Enable(1)
				}
			MAX-ACCESS read-write
			STATUS current
			DESCRIPTION
				"Description."
			::= { gponOnuWanConfigDataModifyEntry 9 }

		
		-- 1.3.6.1.4.1.34592.1.5.1.1.2.18.23.1.10
		gponOnuWanModifyDataAutomaticallyGetDnsv6Address OBJECT-TYPE
			SYNTAX INTEGER
				{
				Disable(0),
				Enable(1)
				}
			MAX-ACCESS read-write
			STATUS current
			DESCRIPTION
				"Description."
			::= { gponOnuWanConfigDataModifyEntry 10 }

		
		-- 1.3.6.1.4.1.34592.1.5.1.1.2.18.23.1.11
		gponOnuWanModifyDataOptionStatus OBJECT-TYPE
			SYNTAX INTEGER
				{
				Disable(0),
				Enable(1)
				}
			MAX-ACCESS read-write
			STATUS current
			DESCRIPTION
				"Description."
			::= { gponOnuWanConfigDataModifyEntry 11 }

		
		-- 1.3.6.1.4.1.34592.1.5.1.1.2.18.23.1.12
		gponOnuWanModifyDataOption60Part1 OBJECT-TYPE
			SYNTAX OCTET STRING
			MAX-ACCESS read-write
			STATUS current
			DESCRIPTION
				"Description."
			::= { gponOnuWanConfigDataModifyEntry 12 }

		
		-- 1.3.6.1.4.1.34592.1.5.1.1.2.18.23.1.13
		gponOnuWanModifyDataOption60Part2 OBJECT-TYPE
			SYNTAX OCTET STRING
			MAX-ACCESS read-write
			STATUS current
			DESCRIPTION
				"Description."
			::= { gponOnuWanConfigDataModifyEntry 13 }

		
		-- 1.3.6.1.4.1.34592.1.5.1.1.2.18.23.1.14
		gponOnuWanModifyDataSync OBJECT-TYPE
			SYNTAX INTEGER { Sync(1) }
			MAX-ACCESS read-write
			STATUS current
			DESCRIPTION
				"Description."
			::= { gponOnuWanConfigDataModifyEntry 14 }

		
		-- 1.3.6.1.4.1.34592.1.5.1.1.2.18.24
		gponOnuProfileCfgTable OBJECT-TYPE
			SYNTAX SEQUENCE OF GponOnuProfileCfgEntry
			MAX-ACCESS not-accessible
			STATUS current
			DESCRIPTION
				"Description."
			::= { gponOnuObjects 24 }

		
		-- 1.3.6.1.4.1.34592.1.5.1.1.2.18.24.1
		gponOnuProfileCfgEntry OBJECT-TYPE
			SYNTAX GponOnuProfileCfgEntry
			MAX-ACCESS not-accessible
			STATUS current
			DESCRIPTION
				"Description."
			INDEX { gponOltDeviceId, gponOltCardId, gponOltPortId, gponOnuId }
			::= { gponOnuProfileCfgTable 1 }

		
		GponOnuProfileCfgEntry ::=
			SEQUENCE { 
				gponOnuOpticalAlarmProfileId
					Integer32
			 }

		-- 1.3.6.1.4.1.34592.1.5.1.1.2.18.24.1.1
		gponOnuOpticalAlarmProfileId OBJECT-TYPE
			SYNTAX Integer32 (1..256 | 65535)
			MAX-ACCESS read-write
			STATUS current
			DESCRIPTION
				"Description."
			::= { gponOnuProfileCfgEntry 1 }

		
		-- 1.3.6.1.4.1.34592.1.5.1.1.2.18.25
		gponOnuMacAddressCollectTable OBJECT-TYPE
			SYNTAX SEQUENCE OF GponOnuMacAddressCollectEntry
			MAX-ACCESS not-accessible
			STATUS current
			DESCRIPTION
				"Description."
			::= { gponOnuObjects 25 }

		
		-- 1.3.6.1.4.1.34592.1.5.1.1.2.18.25.1
		gponOnuMacAddressCollectEntry OBJECT-TYPE
			SYNTAX GponOnuMacAddressCollectEntry
			MAX-ACCESS not-accessible
			STATUS current
			DESCRIPTION
				"Description."
			INDEX { gponOnuMacAddressCollectIndex }
			::= { gponOnuMacAddressCollectTable 1 }

		
		GponOnuMacAddressCollectEntry ::=
			SEQUENCE { 
				gponOnuMacAddressCollectIndex
					Integer32,
				gponOnuMacAddressCollectInfo
					OCTET STRING
			 }

		-- 1.3.6.1.4.1.34592.1.5.1.1.2.18.25.1.1
		gponOnuMacAddressCollectIndex OBJECT-TYPE
			SYNTAX Integer32
			MAX-ACCESS not-accessible
			STATUS current
			DESCRIPTION
				"Description."
			::= { gponOnuMacAddressCollectEntry 1 }

		
		-- 1.3.6.1.4.1.34592.1.5.1.1.2.18.25.1.2
		gponOnuMacAddressCollectInfo OBJECT-TYPE
			SYNTAX OCTET STRING
			MAX-ACCESS read-only
			STATUS current
			DESCRIPTION
				"Description."
			::= { gponOnuMacAddressCollectEntry 2 }

--  1.3.6.1.4.1.34592.1.5.1.1.2.19
		-- 1.3.6.1.4.1.34592.1.5.1.1.2.19
		gponOnuEthPortObjects OBJECT IDENTIFIER ::= { gponControlObjects 19 }

		
		-- 1.3.6.1.4.1.34592.1.5.1.1.2.19.1
		gponOnuEthPortCfgTable OBJECT-TYPE
			SYNTAX SEQUENCE OF GponOnuEthPortCfgEntry
			MAX-ACCESS not-accessible
			STATUS current
			DESCRIPTION
				"Description."
			::= { gponOnuEthPortObjects 1 }

		
		-- 1.3.6.1.4.1.34592.1.5.1.1.2.19.1.1
		gponOnuEthPortCfgEntry OBJECT-TYPE
			SYNTAX GponOnuEthPortCfgEntry
			MAX-ACCESS not-accessible
			STATUS current
			DESCRIPTION
				"Description."
			INDEX { gponOltDeviceId, gponOltCardId, gponOltPortId, gponOnuId, gponOnuEthPortId
				 }
			::= { gponOnuEthPortCfgTable 1 }

		
		GponOnuEthPortCfgEntry ::=
			SEQUENCE { 
				gponOnuEthPortId
					GponOnuEthPortId,
				gponOnuEthPortNativeVlanId
					GponVlanId,
				gponOnuEthPortNativeVlanPriority
					GponVlanPriority,
				gponOnuEthPortInboundCarId
					Integer32,
				gponOnuEthPortOutboundCarId
					Integer32,
				gponOnuEthPortSpeedAndDuplex
					INTEGER,
				gponOnuEthPortFlowCtrl
					GponSwitch,
				gponOnuEthPortOperationalState
					GponSwitch
			 }

		-- 1.3.6.1.4.1.34592.1.5.1.1.2.19.1.1.1
		gponOnuEthPortId OBJECT-TYPE
			SYNTAX GponOnuEthPortId
			MAX-ACCESS read-write
			STATUS current
			DESCRIPTION
				"Description."
			::= { gponOnuEthPortCfgEntry 1 }

		
		-- 1.3.6.1.4.1.34592.1.5.1.1.2.19.1.1.2
		gponOnuEthPortNativeVlanId OBJECT-TYPE
			SYNTAX GponVlanId
			MAX-ACCESS read-write
			STATUS current
			DESCRIPTION
				"Description."
			::= { gponOnuEthPortCfgEntry 2 }

		
		-- 1.3.6.1.4.1.34592.1.5.1.1.2.19.1.1.3
		gponOnuEthPortNativeVlanPriority OBJECT-TYPE
			SYNTAX GponVlanPriority
			MAX-ACCESS read-write
			STATUS current
			DESCRIPTION
				"Description."
			::= { gponOnuEthPortCfgEntry 3 }

		
		-- 1.3.6.1.4.1.34592.1.5.1.1.2.19.1.1.4
		gponOnuEthPortInboundCarId OBJECT-TYPE
			SYNTAX Integer32 (1..256 | 65535)
			MAX-ACCESS read-write
			STATUS current
			DESCRIPTION
				"Description."
			::= { gponOnuEthPortCfgEntry 4 }

		
		-- 1.3.6.1.4.1.34592.1.5.1.1.2.19.1.1.5
		gponOnuEthPortOutboundCarId OBJECT-TYPE
			SYNTAX Integer32 (1..256 | 65535)
			MAX-ACCESS read-write
			STATUS current
			DESCRIPTION
				"Description."
			::= { gponOnuEthPortCfgEntry 5 }

		
		-- 1.3.6.1.4.1.34592.1.5.1.1.2.19.1.1.6
		gponOnuEthPortSpeedAndDuplex OBJECT-TYPE
			SYNTAX INTEGER
				{
				autoNeg(0),
				full10(1),
				full100(2),
				full1000(3),
				half10(17),
				half100(18),
				half1000(19)
				}
			MAX-ACCESS read-write
			STATUS current
			DESCRIPTION
				"Description."
			::= { gponOnuEthPortCfgEntry 6 }

		
		-- 1.3.6.1.4.1.34592.1.5.1.1.2.19.1.1.8
		gponOnuEthPortFlowCtrl OBJECT-TYPE
			SYNTAX GponSwitch
			MAX-ACCESS read-write
			STATUS current
			DESCRIPTION
				"Description."
			::= { gponOnuEthPortCfgEntry 8 }

		
		-- 1.3.6.1.4.1.34592.1.5.1.1.2.19.1.1.9
		gponOnuEthPortOperationalState OBJECT-TYPE
			SYNTAX GponSwitch
			MAX-ACCESS read-write
			STATUS current
			DESCRIPTION
				"Description."
			::= { gponOnuEthPortCfgEntry 9 }

		
		-- 1.3.6.1.4.1.34592.1.5.1.1.2.19.2
		gponOnuEthPortInfoTable OBJECT-TYPE
			SYNTAX SEQUENCE OF GponOnuEthPortInfoEntry
			MAX-ACCESS not-accessible
			STATUS current
			DESCRIPTION
				"Description."
			::= { gponOnuEthPortObjects 2 }

		
		-- 1.3.6.1.4.1.34592.1.5.1.1.2.19.2.1
		gponOnuEthPortInfoEntry OBJECT-TYPE
			SYNTAX GponOnuEthPortInfoEntry
			MAX-ACCESS not-accessible
			STATUS current
			DESCRIPTION
				"Description."
			INDEX { gponOltDeviceId, gponOltCardId, gponOltPortId, gponOnuId, gponOnuEthPortId
				 }
			::= { gponOnuEthPortInfoTable 1 }

		
		GponOnuEthPortInfoEntry ::=
			SEQUENCE { 
				gponOnuEthPortSpeedAndDuplexInfo
					INTEGER,
				gponOnuEthPortState
					INTEGER
			 }

		-- 1.3.6.1.4.1.34592.1.5.1.1.2.19.2.1.1
		gponOnuEthPortSpeedAndDuplexInfo OBJECT-TYPE
			SYNTAX INTEGER
				{
				full10(1),
				full100(2),
				full1000(3),
				half10(17),
				half100(18),
				half1000(19)
				}
			MAX-ACCESS read-only
			STATUS current
			DESCRIPTION
				"Description."
			::= { gponOnuEthPortInfoEntry 1 }

		
		-- 1.3.6.1.4.1.34592.1.5.1.1.2.19.2.1.2
		gponOnuEthPortState OBJECT-TYPE
			SYNTAX INTEGER
				{
				up(1),
				down(2)
				}
			MAX-ACCESS read-only
			STATUS current
			DESCRIPTION
				"Description."
			::= { gponOnuEthPortInfoEntry 2 }

		
		-- 1.3.6.1.4.1.34592.1.5.1.1.2.19.3
		gponOnuEthPortMacAddressTable OBJECT-TYPE
			SYNTAX SEQUENCE OF GponOnuEthPortMacAddressEntry
			MAX-ACCESS not-accessible
			STATUS current
			DESCRIPTION
				"Description."
			::= { gponOnuEthPortObjects 3 }

		
		-- 1.3.6.1.4.1.34592.1.5.1.1.2.19.3.1
		gponOnuEthPortMacAddressEntry OBJECT-TYPE
			SYNTAX GponOnuEthPortMacAddressEntry
			MAX-ACCESS not-accessible
			STATUS current
			DESCRIPTION
				"Description."
			INDEX { gponOltDeviceId, gponOltCardId, gponOltPortId, gponOnuId, gponOnuEthPortId, 
				gponOnuEthPortMacAddressId }
			::= { gponOnuEthPortMacAddressTable 1 }

		
		GponOnuEthPortMacAddressEntry ::=
			SEQUENCE { 
				gponOnuEthPortMacAddressId
					Integer32,
				gponOnuEthPortMacAddress
					GponMac
			 }

		-- 1.3.6.1.4.1.34592.1.5.1.1.2.19.3.1.1
		gponOnuEthPortMacAddressId OBJECT-TYPE
			SYNTAX Integer32
			MAX-ACCESS not-accessible
			STATUS current
			DESCRIPTION
				"Description."
			::= { gponOnuEthPortMacAddressEntry 1 }

		
		-- 1.3.6.1.4.1.34592.1.5.1.1.2.19.3.1.2
		gponOnuEthPortMacAddress OBJECT-TYPE
			SYNTAX GponMac
			MAX-ACCESS read-only
			STATUS current
			DESCRIPTION
				"Description."
			::= { gponOnuEthPortMacAddressEntry 2 }

		
		-- 1.3.6.1.4.1.34592.1.5.1.1.2.19.5
		gponOnuEthPortRTInfoTable OBJECT-TYPE
			SYNTAX SEQUENCE OF GponOnuEthPortRTInfoEntry
			MAX-ACCESS not-accessible
			STATUS current
			DESCRIPTION
				"Description."
			::= { gponOnuEthPortObjects 5 }

		
		-- 1.3.6.1.4.1.34592.1.5.1.1.2.19.5.1
		gponOnuEthPortRTInfoEntry OBJECT-TYPE
			SYNTAX GponOnuEthPortRTInfoEntry
			MAX-ACCESS not-accessible
			STATUS current
			DESCRIPTION
				"Description."
			INDEX { gponOltDeviceId, gponOltCardId, gponOltPortId, gponOnuId, gponOnuEthPortId
				 }
			::= { gponOnuEthPortRTInfoTable 1 }

		
		GponOnuEthPortRTInfoEntry ::=
			SEQUENCE { 
				gponOnuEthPortStatusInfo
					OCTET STRING,
				gponOnuEthPortRTInfoOnuIndex
					Integer32,
				gponOnuEthPortRTInfoPortId
					Integer32
			 }

		-- 1.3.6.1.4.1.34592.1.5.1.1.2.19.5.1.1
		gponOnuEthPortStatusInfo OBJECT-TYPE
			SYNTAX OCTET STRING
			MAX-ACCESS read-write
			STATUS current
			DESCRIPTION
				"Byte 1: type {fe(24), ge(47), unknown(255)}
				2: speed duplex {full10(1), full100(2), full1000(3), half10(17), half100(18), half1000(19), unknown}
				3: link state {up(1), down(2), unknown(255)}
				"
			::= { gponOnuEthPortRTInfoEntry 1 }

		
		-- 1.3.6.1.4.1.34592.1.5.1.1.2.19.5.1.2
		gponOnuEthPortRTInfoOnuIndex OBJECT-TYPE
			SYNTAX Integer32
			MAX-ACCESS read-only
			STATUS current
			DESCRIPTION
				"Description."
			::= { gponOnuEthPortRTInfoEntry 2 }

		
		-- 1.3.6.1.4.1.34592.1.5.1.1.2.19.5.1.3
		gponOnuEthPortRTInfoPortId OBJECT-TYPE
			SYNTAX Integer32
			MAX-ACCESS read-only
			STATUS current
			DESCRIPTION
				"Description."
			::= { gponOnuEthPortRTInfoEntry 3 }

		
		-- 1.3.6.1.4.1.34592.1.5.1.1.2.19.6
		gponOnuEthCurStats15Table OBJECT-TYPE
			SYNTAX SEQUENCE OF GponOnuEthCurStats15Entry
			MAX-ACCESS not-accessible
			STATUS current
			DESCRIPTION
				"Description."
			::= { gponOnuEthPortObjects 6 }

		
		-- 1.3.6.1.4.1.34592.1.5.1.1.2.19.6.1
		gponOnuEthCurStats15Entry OBJECT-TYPE
			SYNTAX GponOnuEthCurStats15Entry
			MAX-ACCESS not-accessible
			STATUS current
			DESCRIPTION
				"Description."
			INDEX { gponOnuEthCurStats15DevIndex, gponOnuEthCurStats15EthPortId }
			::= { gponOnuEthCurStats15Table 1 }

		
		GponOnuEthCurStats15Entry ::=
			SEQUENCE { 
				gponOnuEthCurStats15DevIndex
					Integer32,
				gponOnuEthCurStats15EthPortId
					Integer32,
				curStats15RxFrames
					Counter64,
				curStats15RxBytes
					Counter64,
				curStats15RxBroadcasrFrames
					Counter64,
				curStats15RxMulticastFrames
					Counter64,
				curStats15Rx64Frames
					Counter64,
				curStats15Rx65to127Frames
					Counter64,
				curStats15Rx128to255Frames
					Counter64,
				curStats15Rx256to511Frames
					Counter64,
				curStats15Rx512to1023Frames
					Counter64,
				curStats15Rx1024to1518Frames
					Counter64,
				curStats15RxCrcErrorFrames
					Counter64,
				curStats15RxCrcUnderSizeFrames
					Counter64,
				curStats15RxOverSizeFrames
					Counter64,
				curStats15RxDsicardedFrames
					Counter64,
				curStats15TxFrames
					Counter64,
				curStats15TxBytes
					Counter64,
				curStats15TxBroadcasrFrames
					Counter64,
				curStats15TxMulticastFrames
					Counter64,
				curStats15Tx64Frames
					Counter64,
				curStats15Tx65to127Frames
					Counter64,
				curStats15Tx128to255Frames
					Counter64,
				curStats15Tx256to511Frames
					Counter64,
				curStats15Tx512to1023Frames
					Counter64,
				curStats15Tx1024to1518Frames
					Counter64,
				curStats15TxCrcErrorFrames
					Counter64,
				curStats15TxUnderSizeFrames
					Counter64,
				curStats15TxOverSizeFrames
					Counter64,
				curStats15TxDsicardedFrames
					Counter64
			 }

		-- 1.3.6.1.4.1.34592.1.5.1.1.2.19.6.1.1
		gponOnuEthCurStats15DevIndex OBJECT-TYPE
			SYNTAX Integer32
			MAX-ACCESS not-accessible
			STATUS current
			DESCRIPTION
				"Description."
			::= { gponOnuEthCurStats15Entry 1 }

		
		-- 1.3.6.1.4.1.34592.1.5.1.1.2.19.6.1.2
		gponOnuEthCurStats15EthPortId OBJECT-TYPE
			SYNTAX Integer32
			MAX-ACCESS not-accessible
			STATUS current
			DESCRIPTION
				"Description."
			::= { gponOnuEthCurStats15Entry 2 }

		
		-- 1.3.6.1.4.1.34592.1.5.1.1.2.19.6.1.3
		curStats15RxFrames OBJECT-TYPE
			SYNTAX Counter64
			MAX-ACCESS read-only
			STATUS current
			DESCRIPTION
				"Description."
			::= { gponOnuEthCurStats15Entry 3 }

		
		-- 1.3.6.1.4.1.34592.1.5.1.1.2.19.6.1.4
		curStats15RxBytes OBJECT-TYPE
			SYNTAX Counter64
			MAX-ACCESS read-only
			STATUS current
			DESCRIPTION
				"Description."
			::= { gponOnuEthCurStats15Entry 4 }

		
		-- 1.3.6.1.4.1.34592.1.5.1.1.2.19.6.1.7
		curStats15RxBroadcasrFrames OBJECT-TYPE
			SYNTAX Counter64
			MAX-ACCESS read-only
			STATUS current
			DESCRIPTION
				"Description."
			::= { gponOnuEthCurStats15Entry 7 }

		
		-- 1.3.6.1.4.1.34592.1.5.1.1.2.19.6.1.8
		curStats15RxMulticastFrames OBJECT-TYPE
			SYNTAX Counter64
			MAX-ACCESS read-only
			STATUS current
			DESCRIPTION
				"Description."
			::= { gponOnuEthCurStats15Entry 8 }

		
		-- 1.3.6.1.4.1.34592.1.5.1.1.2.19.6.1.9
		curStats15Rx64Frames OBJECT-TYPE
			SYNTAX Counter64
			MAX-ACCESS read-only
			STATUS current
			DESCRIPTION
				"Description."
			::= { gponOnuEthCurStats15Entry 9 }

		
		-- 1.3.6.1.4.1.34592.1.5.1.1.2.19.6.1.10
		curStats15Rx65to127Frames OBJECT-TYPE
			SYNTAX Counter64
			MAX-ACCESS read-only
			STATUS current
			DESCRIPTION
				"Description."
			::= { gponOnuEthCurStats15Entry 10 }

		
		-- 1.3.6.1.4.1.34592.1.5.1.1.2.19.6.1.11
		curStats15Rx128to255Frames OBJECT-TYPE
			SYNTAX Counter64
			MAX-ACCESS read-only
			STATUS current
			DESCRIPTION
				"Description."
			::= { gponOnuEthCurStats15Entry 11 }

		
		-- 1.3.6.1.4.1.34592.1.5.1.1.2.19.6.1.12
		curStats15Rx256to511Frames OBJECT-TYPE
			SYNTAX Counter64
			MAX-ACCESS read-only
			STATUS current
			DESCRIPTION
				"Description."
			::= { gponOnuEthCurStats15Entry 12 }

		
		-- 1.3.6.1.4.1.34592.1.5.1.1.2.19.6.1.13
		curStats15Rx512to1023Frames OBJECT-TYPE
			SYNTAX Counter64
			MAX-ACCESS read-only
			STATUS current
			DESCRIPTION
				"Description."
			::= { gponOnuEthCurStats15Entry 13 }

		
		-- 1.3.6.1.4.1.34592.1.5.1.1.2.19.6.1.14
		curStats15Rx1024to1518Frames OBJECT-TYPE
			SYNTAX Counter64
			MAX-ACCESS read-only
			STATUS current
			DESCRIPTION
				"Description."
			::= { gponOnuEthCurStats15Entry 14 }

		
		-- 1.3.6.1.4.1.34592.1.5.1.1.2.19.6.1.15
		curStats15RxCrcErrorFrames OBJECT-TYPE
			SYNTAX Counter64
			MAX-ACCESS read-only
			STATUS current
			DESCRIPTION
				"Description."
			::= { gponOnuEthCurStats15Entry 15 }

		
		-- 1.3.6.1.4.1.34592.1.5.1.1.2.19.6.1.16
		curStats15RxCrcUnderSizeFrames OBJECT-TYPE
			SYNTAX Counter64
			MAX-ACCESS read-only
			STATUS current
			DESCRIPTION
				"Description."
			::= { gponOnuEthCurStats15Entry 16 }

		
		-- 1.3.6.1.4.1.34592.1.5.1.1.2.19.6.1.17
		curStats15RxOverSizeFrames OBJECT-TYPE
			SYNTAX Counter64
			MAX-ACCESS read-only
			STATUS current
			DESCRIPTION
				"Description."
			::= { gponOnuEthCurStats15Entry 17 }

		
		-- 1.3.6.1.4.1.34592.1.5.1.1.2.19.6.1.18
		curStats15RxDsicardedFrames OBJECT-TYPE
			SYNTAX Counter64
			MAX-ACCESS read-only
			STATUS current
			DESCRIPTION
				"Description."
			::= { gponOnuEthCurStats15Entry 18 }

		
		-- 1.3.6.1.4.1.34592.1.5.1.1.2.19.6.1.19
		curStats15TxFrames OBJECT-TYPE
			SYNTAX Counter64
			MAX-ACCESS read-only
			STATUS current
			DESCRIPTION
				"Description."
			::= { gponOnuEthCurStats15Entry 19 }

		
		-- 1.3.6.1.4.1.34592.1.5.1.1.2.19.6.1.20
		curStats15TxBytes OBJECT-TYPE
			SYNTAX Counter64
			MAX-ACCESS read-only
			STATUS current
			DESCRIPTION
				"Description."
			::= { gponOnuEthCurStats15Entry 20 }

		
		-- 1.3.6.1.4.1.34592.1.5.1.1.2.19.6.1.21
		curStats15TxBroadcasrFrames OBJECT-TYPE
			SYNTAX Counter64
			MAX-ACCESS read-only
			STATUS current
			DESCRIPTION
				"Description."
			::= { gponOnuEthCurStats15Entry 21 }

		
		-- 1.3.6.1.4.1.34592.1.5.1.1.2.19.6.1.22
		curStats15TxMulticastFrames OBJECT-TYPE
			SYNTAX Counter64
			MAX-ACCESS read-only
			STATUS current
			DESCRIPTION
				"Description."
			::= { gponOnuEthCurStats15Entry 22 }

		
		-- 1.3.6.1.4.1.34592.1.5.1.1.2.19.6.1.23
		curStats15Tx64Frames OBJECT-TYPE
			SYNTAX Counter64
			MAX-ACCESS read-only
			STATUS current
			DESCRIPTION
				"Description."
			::= { gponOnuEthCurStats15Entry 23 }

		
		-- 1.3.6.1.4.1.34592.1.5.1.1.2.19.6.1.24
		curStats15Tx65to127Frames OBJECT-TYPE
			SYNTAX Counter64
			MAX-ACCESS read-only
			STATUS current
			DESCRIPTION
				"Description."
			::= { gponOnuEthCurStats15Entry 24 }

		
		-- 1.3.6.1.4.1.34592.1.5.1.1.2.19.6.1.25
		curStats15Tx128to255Frames OBJECT-TYPE
			SYNTAX Counter64
			MAX-ACCESS read-only
			STATUS current
			DESCRIPTION
				"Description."
			::= { gponOnuEthCurStats15Entry 25 }

		
		-- 1.3.6.1.4.1.34592.1.5.1.1.2.19.6.1.26
		curStats15Tx256to511Frames OBJECT-TYPE
			SYNTAX Counter64
			MAX-ACCESS read-only
			STATUS current
			DESCRIPTION
				"Description."
			::= { gponOnuEthCurStats15Entry 26 }

		
		-- 1.3.6.1.4.1.34592.1.5.1.1.2.19.6.1.27
		curStats15Tx512to1023Frames OBJECT-TYPE
			SYNTAX Counter64
			MAX-ACCESS read-only
			STATUS current
			DESCRIPTION
				"Description."
			::= { gponOnuEthCurStats15Entry 27 }

		
		-- 1.3.6.1.4.1.34592.1.5.1.1.2.19.6.1.28
		curStats15Tx1024to1518Frames OBJECT-TYPE
			SYNTAX Counter64
			MAX-ACCESS read-only
			STATUS current
			DESCRIPTION
				"Description."
			::= { gponOnuEthCurStats15Entry 28 }

		
		-- 1.3.6.1.4.1.34592.1.5.1.1.2.19.6.1.29
		curStats15TxCrcErrorFrames OBJECT-TYPE
			SYNTAX Counter64
			MAX-ACCESS read-only
			STATUS current
			DESCRIPTION
				"Description."
			::= { gponOnuEthCurStats15Entry 29 }

		
		-- 1.3.6.1.4.1.34592.1.5.1.1.2.19.6.1.30
		curStats15TxUnderSizeFrames OBJECT-TYPE
			SYNTAX Counter64
			MAX-ACCESS read-only
			STATUS current
			DESCRIPTION
				"Description."
			::= { gponOnuEthCurStats15Entry 30 }

		
		-- 1.3.6.1.4.1.34592.1.5.1.1.2.19.6.1.31
		curStats15TxOverSizeFrames OBJECT-TYPE
			SYNTAX Counter64
			MAX-ACCESS read-only
			STATUS current
			DESCRIPTION
				"Description."
			::= { gponOnuEthCurStats15Entry 31 }

		
		-- 1.3.6.1.4.1.34592.1.5.1.1.2.19.6.1.32
		curStats15TxDsicardedFrames OBJECT-TYPE
			SYNTAX Counter64
			MAX-ACCESS read-only
			STATUS current
			DESCRIPTION
				"Description."
			::= { gponOnuEthCurStats15Entry 32 }

		
		-- 1.3.6.1.4.1.34592.1.5.1.1.2.19.7
		gponOnuEthHisStats15Table OBJECT-TYPE
			SYNTAX SEQUENCE OF GponOnuEthHisStats15Entry
			MAX-ACCESS not-accessible
			STATUS current
			DESCRIPTION
				"Description."
			::= { gponOnuEthPortObjects 7 }

		
		-- 1.3.6.1.4.1.34592.1.5.1.1.2.19.7.1
		gponOnuEthHisStats15Entry OBJECT-TYPE
			SYNTAX GponOnuEthHisStats15Entry
			MAX-ACCESS not-accessible
			STATUS current
			DESCRIPTION
				"Description."
			INDEX { gponOnuEthHisStats15DevIndex, gponOnuEthHisStats15EthPortId }
			::= { gponOnuEthHisStats15Table 1 }

		
		GponOnuEthHisStats15Entry ::=
			SEQUENCE { 
				gponOnuEthHisStats15DevIndex
					Integer32,
				gponOnuEthHisStats15EthPortId
					Integer32,
				hisStats15RxFrames
					Counter64,
				hisStats15RxBytes
					Counter64,
				hisStats15RxBroadcasrFrames
					Counter64,
				hisStats15RxMulticastFrames
					Counter64,
				hisStats15Rx64Frames
					Counter64,
				hisStats15Rx65to127Frames
					Counter64,
				hisStats15Rx128to255Frames
					Counter64,
				hisStats15Rx256to511Frames
					Counter64,
				hisStats15Rx512to1023Frames
					Counter64,
				hisStats15Rx1024to1518Frames
					Counter64,
				hisStats15RxCrcErrorFrames
					Counter64,
				hisStats15RxCrcUnderSizeFrames
					Counter64,
				hisStats15RxOverSizeFrames
					Counter64,
				hisStats15RxDsicardedFrames
					Counter64,
				hisStats15TxFrames
					Counter64,
				hisStats15TxBytes
					Counter64,
				hisStats15TxBroadcasrFrames
					Counter64,
				hisStats15TxMulticastFrames
					Counter64,
				hisStats15Tx64Frames
					Counter64,
				hisStats15Tx65to127Frames
					Counter64,
				hisStats15Tx128to255Frames
					Counter64,
				hisStats15Tx256to511Frames
					Counter64,
				hisStats15Tx512to1023Frames
					Counter64,
				hisStats15Tx1024to1518Frames
					Counter64,
				hisStats15TxCrcErrorFrames
					Counter64,
				hisStats15TxUnderSizeFrames
					Counter64,
				hisStats15TxOverSizeFrames
					Counter64,
				hisStats15TxDsicardedFrames
					Counter64
			 }

		-- 1.3.6.1.4.1.34592.1.5.1.1.2.19.7.1.1
		gponOnuEthHisStats15DevIndex OBJECT-TYPE
			SYNTAX Integer32
			MAX-ACCESS not-accessible
			STATUS current
			DESCRIPTION
				"Description."
			::= { gponOnuEthHisStats15Entry 1 }

		
		-- 1.3.6.1.4.1.34592.1.5.1.1.2.19.7.1.2
		gponOnuEthHisStats15EthPortId OBJECT-TYPE
			SYNTAX Integer32
			MAX-ACCESS not-accessible
			STATUS current
			DESCRIPTION
				"Description."
			::= { gponOnuEthHisStats15Entry 2 }

		
		-- 1.3.6.1.4.1.34592.1.5.1.1.2.19.7.1.3
		hisStats15RxFrames OBJECT-TYPE
			SYNTAX Counter64
			MAX-ACCESS read-only
			STATUS current
			DESCRIPTION
				"Description."
			::= { gponOnuEthHisStats15Entry 3 }

		
		-- 1.3.6.1.4.1.34592.1.5.1.1.2.19.7.1.4
		hisStats15RxBytes OBJECT-TYPE
			SYNTAX Counter64
			MAX-ACCESS read-only
			STATUS current
			DESCRIPTION
				"Description."
			::= { gponOnuEthHisStats15Entry 4 }

		
		-- 1.3.6.1.4.1.34592.1.5.1.1.2.19.7.1.5
		hisStats15RxBroadcasrFrames OBJECT-TYPE
			SYNTAX Counter64
			MAX-ACCESS read-only
			STATUS current
			DESCRIPTION
				"Description."
			::= { gponOnuEthHisStats15Entry 5 }

		
		-- 1.3.6.1.4.1.34592.1.5.1.1.2.19.7.1.6
		hisStats15RxMulticastFrames OBJECT-TYPE
			SYNTAX Counter64
			MAX-ACCESS read-only
			STATUS current
			DESCRIPTION
				"Description."
			::= { gponOnuEthHisStats15Entry 6 }

		
		-- 1.3.6.1.4.1.34592.1.5.1.1.2.19.7.1.7
		hisStats15Rx64Frames OBJECT-TYPE
			SYNTAX Counter64
			MAX-ACCESS read-only
			STATUS current
			DESCRIPTION
				"Description."
			::= { gponOnuEthHisStats15Entry 7 }

		
		-- 1.3.6.1.4.1.34592.1.5.1.1.2.19.7.1.8
		hisStats15Rx65to127Frames OBJECT-TYPE
			SYNTAX Counter64
			MAX-ACCESS read-only
			STATUS current
			DESCRIPTION
				"Description."
			::= { gponOnuEthHisStats15Entry 8 }

		
		-- 1.3.6.1.4.1.34592.1.5.1.1.2.19.7.1.9
		hisStats15Rx128to255Frames OBJECT-TYPE
			SYNTAX Counter64
			MAX-ACCESS read-only
			STATUS current
			DESCRIPTION
				"Description."
			::= { gponOnuEthHisStats15Entry 9 }

		
		-- 1.3.6.1.4.1.34592.1.5.1.1.2.19.7.1.10
		hisStats15Rx256to511Frames OBJECT-TYPE
			SYNTAX Counter64
			MAX-ACCESS read-only
			STATUS current
			DESCRIPTION
				"Description."
			::= { gponOnuEthHisStats15Entry 10 }

		
		-- 1.3.6.1.4.1.34592.1.5.1.1.2.19.7.1.11
		hisStats15Rx512to1023Frames OBJECT-TYPE
			SYNTAX Counter64
			MAX-ACCESS read-only
			STATUS current
			DESCRIPTION
				"Description."
			::= { gponOnuEthHisStats15Entry 11 }

		
		-- 1.3.6.1.4.1.34592.1.5.1.1.2.19.7.1.12
		hisStats15Rx1024to1518Frames OBJECT-TYPE
			SYNTAX Counter64
			MAX-ACCESS read-only
			STATUS current
			DESCRIPTION
				"Description."
			::= { gponOnuEthHisStats15Entry 12 }

		
		-- 1.3.6.1.4.1.34592.1.5.1.1.2.19.7.1.13
		hisStats15RxCrcErrorFrames OBJECT-TYPE
			SYNTAX Counter64
			MAX-ACCESS read-only
			STATUS current
			DESCRIPTION
				"Description."
			::= { gponOnuEthHisStats15Entry 13 }

		
		-- 1.3.6.1.4.1.34592.1.5.1.1.2.19.7.1.14
		hisStats15RxCrcUnderSizeFrames OBJECT-TYPE
			SYNTAX Counter64
			MAX-ACCESS read-only
			STATUS current
			DESCRIPTION
				"Description."
			::= { gponOnuEthHisStats15Entry 14 }

		
		-- 1.3.6.1.4.1.34592.1.5.1.1.2.19.7.1.15
		hisStats15RxOverSizeFrames OBJECT-TYPE
			SYNTAX Counter64
			MAX-ACCESS read-only
			STATUS current
			DESCRIPTION
				"Description."
			::= { gponOnuEthHisStats15Entry 15 }

		
		-- 1.3.6.1.4.1.34592.1.5.1.1.2.19.7.1.16
		hisStats15RxDsicardedFrames OBJECT-TYPE
			SYNTAX Counter64
			MAX-ACCESS read-only
			STATUS current
			DESCRIPTION
				"Description."
			::= { gponOnuEthHisStats15Entry 16 }

		
		-- 1.3.6.1.4.1.34592.1.5.1.1.2.19.7.1.17
		hisStats15TxFrames OBJECT-TYPE
			SYNTAX Counter64
			MAX-ACCESS read-only
			STATUS current
			DESCRIPTION
				"Description."
			::= { gponOnuEthHisStats15Entry 17 }

		
		-- 1.3.6.1.4.1.34592.1.5.1.1.2.19.7.1.18
		hisStats15TxBytes OBJECT-TYPE
			SYNTAX Counter64
			MAX-ACCESS read-only
			STATUS current
			DESCRIPTION
				"Description."
			::= { gponOnuEthHisStats15Entry 18 }

		
		-- 1.3.6.1.4.1.34592.1.5.1.1.2.19.7.1.19
		hisStats15TxBroadcasrFrames OBJECT-TYPE
			SYNTAX Counter64
			MAX-ACCESS read-only
			STATUS current
			DESCRIPTION
				"Description."
			::= { gponOnuEthHisStats15Entry 19 }

		
		-- 1.3.6.1.4.1.34592.1.5.1.1.2.19.7.1.20
		hisStats15TxMulticastFrames OBJECT-TYPE
			SYNTAX Counter64
			MAX-ACCESS read-only
			STATUS current
			DESCRIPTION
				"Description."
			::= { gponOnuEthHisStats15Entry 20 }

		
		-- 1.3.6.1.4.1.34592.1.5.1.1.2.19.7.1.21
		hisStats15Tx64Frames OBJECT-TYPE
			SYNTAX Counter64
			MAX-ACCESS read-only
			STATUS current
			DESCRIPTION
				"Description."
			::= { gponOnuEthHisStats15Entry 21 }

		
		-- 1.3.6.1.4.1.34592.1.5.1.1.2.19.7.1.22
		hisStats15Tx65to127Frames OBJECT-TYPE
			SYNTAX Counter64
			MAX-ACCESS read-only
			STATUS current
			DESCRIPTION
				"Description."
			::= { gponOnuEthHisStats15Entry 22 }

		
		-- 1.3.6.1.4.1.34592.1.5.1.1.2.19.7.1.23
		hisStats15Tx128to255Frames OBJECT-TYPE
			SYNTAX Counter64
			MAX-ACCESS read-only
			STATUS current
			DESCRIPTION
				"Description."
			::= { gponOnuEthHisStats15Entry 23 }

		
		-- 1.3.6.1.4.1.34592.1.5.1.1.2.19.7.1.24
		hisStats15Tx256to511Frames OBJECT-TYPE
			SYNTAX Counter64
			MAX-ACCESS read-only
			STATUS current
			DESCRIPTION
				"Description."
			::= { gponOnuEthHisStats15Entry 24 }

		
		-- 1.3.6.1.4.1.34592.1.5.1.1.2.19.7.1.25
		hisStats15Tx512to1023Frames OBJECT-TYPE
			SYNTAX Counter64
			MAX-ACCESS read-only
			STATUS current
			DESCRIPTION
				"Description."
			::= { gponOnuEthHisStats15Entry 25 }

		
		-- 1.3.6.1.4.1.34592.1.5.1.1.2.19.7.1.26
		hisStats15Tx1024to1518Frames OBJECT-TYPE
			SYNTAX Counter64
			MAX-ACCESS read-only
			STATUS current
			DESCRIPTION
				"Description."
			::= { gponOnuEthHisStats15Entry 26 }

		
		-- 1.3.6.1.4.1.34592.1.5.1.1.2.19.7.1.27
		hisStats15TxCrcErrorFrames OBJECT-TYPE
			SYNTAX Counter64
			MAX-ACCESS read-only
			STATUS current
			DESCRIPTION
				"Description."
			::= { gponOnuEthHisStats15Entry 27 }

		
		-- 1.3.6.1.4.1.34592.1.5.1.1.2.19.7.1.28
		hisStats15TxUnderSizeFrames OBJECT-TYPE
			SYNTAX Counter64
			MAX-ACCESS read-only
			STATUS current
			DESCRIPTION
				"Description."
			::= { gponOnuEthHisStats15Entry 28 }

		
		-- 1.3.6.1.4.1.34592.1.5.1.1.2.19.7.1.29
		hisStats15TxOverSizeFrames OBJECT-TYPE
			SYNTAX Counter64
			MAX-ACCESS read-only
			STATUS current
			DESCRIPTION
				"Description."
			::= { gponOnuEthHisStats15Entry 29 }

		
		-- 1.3.6.1.4.1.34592.1.5.1.1.2.19.7.1.30
		hisStats15TxDsicardedFrames OBJECT-TYPE
			SYNTAX Counter64
			MAX-ACCESS read-only
			STATUS current
			DESCRIPTION
				"Description."
			::= { gponOnuEthHisStats15Entry 30 }

		
		-- 1.3.6.1.4.1.34592.1.5.1.1.2.19.8
		gponOnuEthCurStats15CollectTable OBJECT-TYPE
			SYNTAX SEQUENCE OF GponOnuEthCurStats15CollectEntry
			MAX-ACCESS not-accessible
			STATUS current
			DESCRIPTION
				"Description."
			::= { gponOnuEthPortObjects 8 }

		
		-- 1.3.6.1.4.1.34592.1.5.1.1.2.19.8.1
		gponOnuEthCurStats15CollectEntry OBJECT-TYPE
			SYNTAX GponOnuEthCurStats15CollectEntry
			MAX-ACCESS not-accessible
			STATUS current
			DESCRIPTION
				"Description."
			INDEX { gponOnuEthCurStats15CollectIndex }
			::= { gponOnuEthCurStats15CollectTable 1 }

		
		GponOnuEthCurStats15CollectEntry ::=
			SEQUENCE { 
				gponOnuEthCurStats15CollectIndex
					Integer32,
				gponOnuEthCurStats15CollectData
					OCTET STRING
			 }

		-- 1.3.6.1.4.1.34592.1.5.1.1.2.19.8.1.1
		gponOnuEthCurStats15CollectIndex OBJECT-TYPE
			SYNTAX Integer32
			MAX-ACCESS not-accessible
			STATUS current
			DESCRIPTION
				"Description."
			::= { gponOnuEthCurStats15CollectEntry 1 }

		
		-- 1.3.6.1.4.1.34592.1.5.1.1.2.19.8.1.2
		gponOnuEthCurStats15CollectData OBJECT-TYPE
			SYNTAX OCTET STRING
			MAX-ACCESS read-write
			STATUS current
			DESCRIPTION
				"Description."
			::= { gponOnuEthCurStats15CollectEntry 2 }

		
		-- 1.3.6.1.4.1.34592.1.5.1.1.2.19.9
		gponOnuEthHisStats15CollectTable OBJECT-TYPE
			SYNTAX SEQUENCE OF GponOnuEthHisStats15CollectEntry
			MAX-ACCESS not-accessible
			STATUS current
			DESCRIPTION
				"Description."
			::= { gponOnuEthPortObjects 9 }

		
		-- 1.3.6.1.4.1.34592.1.5.1.1.2.19.9.1
		gponOnuEthHisStats15CollectEntry OBJECT-TYPE
			SYNTAX GponOnuEthHisStats15CollectEntry
			MAX-ACCESS not-accessible
			STATUS current
			DESCRIPTION
				"Description."
			INDEX { gponOnuEthHisStats15CollectIndex }
			::= { gponOnuEthHisStats15CollectTable 1 }

		
		GponOnuEthHisStats15CollectEntry ::=
			SEQUENCE { 
				gponOnuEthHisStats15CollectIndex
					Integer32,
				gponOnuEthHisStats15CollectData
					OCTET STRING
			 }

		-- 1.3.6.1.4.1.34592.1.5.1.1.2.19.9.1.1
		gponOnuEthHisStats15CollectIndex OBJECT-TYPE
			SYNTAX Integer32
			MAX-ACCESS not-accessible
			STATUS current
			DESCRIPTION
				"Description."
			::= { gponOnuEthHisStats15CollectEntry 1 }

		
		-- 1.3.6.1.4.1.34592.1.5.1.1.2.19.9.1.2
		gponOnuEthHisStats15CollectData OBJECT-TYPE
			SYNTAX OCTET STRING
			MAX-ACCESS read-write
			STATUS current
			DESCRIPTION
				"Description."
			::= { gponOnuEthHisStats15CollectEntry 2 }

			-- 1.3.6.1.4.1.34592.1.5.1.1.2.19.10
		gponOnuEthMcGroupInfoCollectTable OBJECT-TYPE
			SYNTAX SEQUENCE OF GponOnuEthMcGroupInfoCollectEntry
			MAX-ACCESS not-accessible
			STATUS current
			DESCRIPTION
				"Description."
			::= { gponOnuEthPortObjects 10 }

		
		-- 1.3.6.1.4.1.34592.1.5.1.1.2.19.10.1
		gponOnuEthMcGroupInfoCollectEntry OBJECT-TYPE
			SYNTAX GponOnuEthMcGroupInfoCollectEntry
			MAX-ACCESS not-accessible
			STATUS current
			DESCRIPTION
				"Description."
			INDEX { gponOnuIEthMcGroupOnundex, gponOnuEthMcGroupInfoCollectIndex }
			::= { gponOnuEthMcGroupInfoCollectTable 1 }

		
		GponOnuEthMcGroupInfoCollectEntry ::=
			SEQUENCE { 
				gponOnuIEthMcGroupOnundex
					Integer32,
				gponOnuEthMcGroupInfoCollectIndex
					Integer32,
				gponOnuEthMcGroupInfoCollectInfo
					OCTET STRING
			 }

		-- 1.3.6.1.4.1.34592.1.5.1.1.2.19.10.1.1
		gponOnuIEthMcGroupOnundex OBJECT-TYPE
			SYNTAX Integer32
			MAX-ACCESS read-only
			STATUS current
			DESCRIPTION
				"Description."
			::= { gponOnuEthMcGroupInfoCollectEntry 1 }

		
		-- 1.3.6.1.4.1.34592.1.5.1.1.2.19.10.1.2
		gponOnuEthMcGroupInfoCollectIndex OBJECT-TYPE
			SYNTAX Integer32
			MAX-ACCESS read-only
			STATUS current
			DESCRIPTION
				"Description."
			::= { gponOnuEthMcGroupInfoCollectEntry 2 }

		
		-- 1.3.6.1.4.1.34592.1.5.1.1.2.19.10.1.4
		gponOnuEthMcGroupInfoCollectInfo OBJECT-TYPE
			SYNTAX OCTET STRING
			MAX-ACCESS read-only
			STATUS current
			DESCRIPTION
				"Description."
			::= { gponOnuEthMcGroupInfoCollectEntry 4 }
		
		-- 1.3.6.1.4.1.34592.1.5.1.1.2.20
		gponOnuPotsPortObjects OBJECT IDENTIFIER ::= { gponControlObjects 20 }

		
		-- 1.3.6.1.4.1.34592.1.5.1.1.2.20.1
		gponOnuPotsPortCfgTable OBJECT-TYPE
			SYNTAX SEQUENCE OF GponOnuPotsPortCfgEntry
			MAX-ACCESS not-accessible
			STATUS current
			DESCRIPTION
				"Description."
			::= { gponOnuPotsPortObjects 1 }

		
		-- 1.3.6.1.4.1.34592.1.5.1.1.2.20.1.1
		gponOnuPotsPortCfgEntry OBJECT-TYPE
			SYNTAX GponOnuPotsPortCfgEntry
			MAX-ACCESS not-accessible
			STATUS current
			DESCRIPTION
				"Description."
			INDEX { gponOltDeviceId, gponOltCardId, gponOltPortId, gponOnuId, gponOnuPotsPortId
				 }
			::= { gponOnuPotsPortCfgTable 1 }

		
		GponOnuPotsPortCfgEntry ::=
			SEQUENCE { 
				gponOnuPotsPortId
					GponOnuPotsPortId,
				gponOnuPotsPortOperationalState
					GponSwitch,
				gponOnuPotsPortCfgPotsProfileId
					GponPotsProfileId,
				gponOnuPotsPortCfgSipAgentProfileId
					GponSipAgentProfileId
			 }

		-- 1.3.6.1.4.1.34592.1.5.1.1.2.20.1.1.1
		gponOnuPotsPortId OBJECT-TYPE
			SYNTAX GponOnuPotsPortId
			MAX-ACCESS read-write
			STATUS current
			DESCRIPTION
				"Description."
			::= { gponOnuPotsPortCfgEntry 1 }

		
		-- 1.3.6.1.4.1.34592.1.5.1.1.2.20.1.1.2
		gponOnuPotsPortOperationalState OBJECT-TYPE
			SYNTAX GponSwitch
			MAX-ACCESS read-write
			STATUS current
			DESCRIPTION
				"Description."
			::= { gponOnuPotsPortCfgEntry 2 }

		
		-- 1.3.6.1.4.1.34592.1.5.1.1.2.20.1.1.3
		gponOnuPotsPortCfgPotsProfileId OBJECT-TYPE
			SYNTAX GponPotsProfileId
			MAX-ACCESS read-write
			STATUS current
			DESCRIPTION
				"Description."
			DEFVAL { 65535 }
			::= { gponOnuPotsPortCfgEntry 3 }

		
		-- 1.3.6.1.4.1.34592.1.5.1.1.2.20.1.1.4
		gponOnuPotsPortCfgSipAgentProfileId OBJECT-TYPE
			SYNTAX GponSipAgentProfileId
			MAX-ACCESS read-write
			STATUS current
			DESCRIPTION
				"Description."
			DEFVAL { 65535 }
			::= { gponOnuPotsPortCfgEntry 4 }

		
		-- 1.3.6.1.4.1.34592.1.5.1.1.2.20.2
		gponOnuIpCfgTable OBJECT-TYPE
			SYNTAX SEQUENCE OF GponOnuIpCfgEntry
			MAX-ACCESS not-accessible
			STATUS current
			DESCRIPTION
				"Description."
			::= { gponOnuPotsPortObjects 2 }

		
		-- 1.3.6.1.4.1.34592.1.5.1.1.2.20.2.1
		gponOnuIpCfgEntry OBJECT-TYPE
			SYNTAX GponOnuIpCfgEntry
			MAX-ACCESS not-accessible
			STATUS current
			DESCRIPTION
				"Description."
			INDEX { gponOltDeviceId, gponOltCardId, gponOltPortId, gponOnuId, gponOnuIpHostId
				 }
			::= { gponOnuIpCfgTable 1 }

		
		GponOnuIpCfgEntry ::=
			SEQUENCE { 
				gponOnuIpHostId
					Integer32,
				gponOnuIpCfgRowStatus
					RowStatus,
				gponOnuIpCfgMode
					INTEGER,
				gponOnuIpCfgVlanId
					Integer32,
				gponOnuIpCfgVlanPri
					Integer32,
				gponOnuIpCfgIp
					IpAddress,
				gponOnuIpCfgMask
					IpAddress,
				gponOnuIpCfgGateway
					IpAddress,
				gponOnuIpCfgPriDns
					IpAddress,
				gponOnuIpCfgSlaveDns
					IpAddress,
				gponOnuIpCfgMacAddress
					GponMac
			 }

		-- 1.3.6.1.4.1.34592.1.5.1.1.2.20.2.1.1
		gponOnuIpHostId OBJECT-TYPE
			SYNTAX Integer32 (1..2)
			MAX-ACCESS not-accessible
			STATUS current
			DESCRIPTION
				"Description."
			::= { gponOnuIpCfgEntry 1 }

		
		-- 1.3.6.1.4.1.34592.1.5.1.1.2.20.2.1.2
		gponOnuIpCfgRowStatus OBJECT-TYPE
			SYNTAX RowStatus
			MAX-ACCESS read-create
			STATUS current
			DESCRIPTION
				"Description."
			::= { gponOnuIpCfgEntry 2 }

		
		-- 1.3.6.1.4.1.34592.1.5.1.1.2.20.2.1.3
		gponOnuIpCfgMode OBJECT-TYPE
			SYNTAX INTEGER
				{
				dhcp(1),
				static(2)
				}
			MAX-ACCESS read-create
			STATUS current
			DESCRIPTION
				"Description."
			::= { gponOnuIpCfgEntry 3 }

		
		-- 1.3.6.1.4.1.34592.1.5.1.1.2.20.2.1.4
		gponOnuIpCfgVlanId OBJECT-TYPE
			SYNTAX Integer32
			MAX-ACCESS read-create
			STATUS current
			DESCRIPTION
				"Description."
			::= { gponOnuIpCfgEntry 4 }

		
		-- 1.3.6.1.4.1.34592.1.5.1.1.2.20.2.1.5
		gponOnuIpCfgVlanPri OBJECT-TYPE
			SYNTAX Integer32
			MAX-ACCESS read-create
			STATUS current
			DESCRIPTION
				"Description."
			::= { gponOnuIpCfgEntry 5 }

		
		-- 1.3.6.1.4.1.34592.1.5.1.1.2.20.2.1.6
		gponOnuIpCfgIp OBJECT-TYPE
			SYNTAX IpAddress
			MAX-ACCESS read-create
			STATUS current
			DESCRIPTION
				"Description."
			::= { gponOnuIpCfgEntry 6 }

		
		-- 1.3.6.1.4.1.34592.1.5.1.1.2.20.2.1.7
		gponOnuIpCfgMask OBJECT-TYPE
			SYNTAX IpAddress
			MAX-ACCESS read-create
			STATUS current
			DESCRIPTION
				"Description."
			::= { gponOnuIpCfgEntry 7 }

		
		-- 1.3.6.1.4.1.34592.1.5.1.1.2.20.2.1.8
		gponOnuIpCfgGateway OBJECT-TYPE
			SYNTAX IpAddress
			MAX-ACCESS read-create
			STATUS current
			DESCRIPTION
				"Description."
			::= { gponOnuIpCfgEntry 8 }

		
		-- 1.3.6.1.4.1.34592.1.5.1.1.2.20.2.1.9
		gponOnuIpCfgPriDns OBJECT-TYPE
			SYNTAX IpAddress
			MAX-ACCESS read-create
			STATUS current
			DESCRIPTION
				"Description."
			::= { gponOnuIpCfgEntry 9 }

		
		-- 1.3.6.1.4.1.34592.1.5.1.1.2.20.2.1.10
		gponOnuIpCfgSlaveDns OBJECT-TYPE
			SYNTAX IpAddress
			MAX-ACCESS read-create
			STATUS current
			DESCRIPTION
				"Description."
			::= { gponOnuIpCfgEntry 10 }

		
		-- 1.3.6.1.4.1.34592.1.5.1.1.2.20.2.1.11
		gponOnuIpCfgMacAddress OBJECT-TYPE
			SYNTAX GponMac
			MAX-ACCESS read-create
			STATUS current
			DESCRIPTION
				"Description."
			::= { gponOnuIpCfgEntry 11 }

		
		-- 1.3.6.1.4.1.34592.1.5.1.1.2.20.3
		gponOnuSipPstnUserTable OBJECT-TYPE
			SYNTAX SEQUENCE OF GponOnuSipPstnUserEntry
			MAX-ACCESS not-accessible
			STATUS current
			DESCRIPTION
				"Description."
			::= { gponOnuPotsPortObjects 3 }

		
		-- 1.3.6.1.4.1.34592.1.5.1.1.2.20.3.1
		gponOnuSipPstnUserEntry OBJECT-TYPE
			SYNTAX GponOnuSipPstnUserEntry
			MAX-ACCESS not-accessible
			STATUS current
			DESCRIPTION
				"Description."
			INDEX { gponOltDeviceId, gponOltCardId, gponOltPortId, gponOnuId, gponOnuSipPstnUserId
				 }
			::= { gponOnuSipPstnUserTable 1 }

		
		GponOnuSipPstnUserEntry ::=
			SEQUENCE { 
				gponOnuSipPstnUserIpHostId
					Unsigned32,
				gponOnuSipPstnUserId
					GponOnuPotsPortId,
				gponOnuSipPstnUserRowStatus
					RowStatus,
				gponOnuSipPstnUserName
					OCTET STRING,
				gponOnuSipPstnUserPassword
					OCTET STRING,
				gponOnuSipPstnUserTelephoneNumber
					OCTET STRING,
				gponOnuSipPstnUserAgentProfileId
					GponSipAgentProfileId,
				gponOnuSipPstnUserDigitMapProfileId
					GponDigitMapProfileId,
				gponOnuSipPstnUserSipRightFlagProfileId
					GponSipRightFlagProfileId
			 }

		-- 1.3.6.1.4.1.34592.1.5.1.1.2.20.3.1.1
		gponOnuSipPstnUserIpHostId OBJECT-TYPE
			SYNTAX Unsigned32
			MAX-ACCESS read-write
			STATUS current
			DESCRIPTION
				"Description."
			::= { gponOnuSipPstnUserEntry 1 }

		
--   1.3.6.1.4.1.34592.1.5.1.1.2.20.3.1.2
-- 1.3.6.1.4.1.34592.1.5.1.1.2.20.3.1.2
		-- 1.3.6.1.4.1.34592.1.5.1.1.2.20.3.1.2
		gponOnuSipPstnUserId OBJECT-TYPE
			SYNTAX GponOnuPotsPortId
			MAX-ACCESS not-accessible
			STATUS current
			DESCRIPTION
				"Description."
			::= { gponOnuSipPstnUserEntry 2 }

		
		-- 1.3.6.1.4.1.34592.1.5.1.1.2.20.3.1.3
		gponOnuSipPstnUserRowStatus OBJECT-TYPE
			SYNTAX RowStatus
			MAX-ACCESS read-create
			STATUS current
			DESCRIPTION
				"Description."
			::= { gponOnuSipPstnUserEntry 3 }

		
		-- 1.3.6.1.4.1.34592.1.5.1.1.2.20.3.1.4
		gponOnuSipPstnUserName OBJECT-TYPE
			SYNTAX OCTET STRING (SIZE (1..32))
			MAX-ACCESS read-create
			STATUS current
			DESCRIPTION
				"Description."
			::= { gponOnuSipPstnUserEntry 4 }

		
		-- 1.3.6.1.4.1.34592.1.5.1.1.2.20.3.1.5
		gponOnuSipPstnUserPassword OBJECT-TYPE
			SYNTAX OCTET STRING (SIZE (1..24))
			MAX-ACCESS read-create
			STATUS current
			DESCRIPTION
				"Description."
			::= { gponOnuSipPstnUserEntry 5 }

		
		-- 1.3.6.1.4.1.34592.1.5.1.1.2.20.3.1.6
		gponOnuSipPstnUserTelephoneNumber OBJECT-TYPE
			SYNTAX OCTET STRING (SIZE (1..31))
			MAX-ACCESS read-create
			STATUS current
			DESCRIPTION
				"Description."
			::= { gponOnuSipPstnUserEntry 6 }

		
		-- 1.3.6.1.4.1.34592.1.5.1.1.2.20.3.1.7
		gponOnuSipPstnUserAgentProfileId OBJECT-TYPE
			SYNTAX GponSipAgentProfileId
			MAX-ACCESS read-create
			STATUS current
			DESCRIPTION
				"Description."
			DEFVAL { 65535 }
			::= { gponOnuSipPstnUserEntry 7 }

		
		-- 1.3.6.1.4.1.34592.1.5.1.1.2.20.3.1.8
		gponOnuSipPstnUserDigitMapProfileId OBJECT-TYPE
			SYNTAX GponDigitMapProfileId
			MAX-ACCESS read-create
			STATUS current
			DESCRIPTION
				"Description."
			DEFVAL { 65535 }
			::= { gponOnuSipPstnUserEntry 8 }

		
		-- 1.3.6.1.4.1.34592.1.5.1.1.2.20.3.1.9
		gponOnuSipPstnUserSipRightFlagProfileId OBJECT-TYPE
			SYNTAX GponSipRightFlagProfileId
			MAX-ACCESS read-create
			STATUS current
			DESCRIPTION
				"Description."
			DEFVAL { 65535 }
			::= { gponOnuSipPstnUserEntry 9 }

		
		-- 1.3.6.1.4.1.34592.1.5.1.1.2.20.4
		gponOnuSipPstnUserInfoTable OBJECT-TYPE
			SYNTAX SEQUENCE OF GponOnuSipPstnUserInfoEntry
			MAX-ACCESS not-accessible
			STATUS current
			DESCRIPTION
				"Description."
			::= { gponOnuPotsPortObjects 4 }

		
		-- 1.3.6.1.4.1.34592.1.5.1.1.2.20.4.1
		gponOnuSipPstnUserInfoEntry OBJECT-TYPE
			SYNTAX GponOnuSipPstnUserInfoEntry
			MAX-ACCESS not-accessible
			STATUS current
			DESCRIPTION
				"Description."
			INDEX { gponOltDeviceId, gponOltCardId, gponOltPortId, gponOnuId, gponOnuSipPstnUserId
				 }
			::= { gponOnuSipPstnUserInfoTable 1 }

		
		GponOnuSipPstnUserInfoEntry ::=
			SEQUENCE { 
				gponOnuSipPstnUserState
					INTEGER,
				gponOnuSipPstnUserHookState
					INTEGER,
				gponOnuSipPstnUserCodec
					DisplayString,
				gponOnuSipPstnUserServerStatus
					DisplayString,
				gponOnuSipPstnUserSessionType
					DisplayString
			 }

		-- 1.3.6.1.4.1.34592.1.5.1.1.2.20.4.1.1
		gponOnuSipPstnUserState OBJECT-TYPE
			SYNTAX INTEGER
				{
				lock(1),
				unlock(2)
				}
			MAX-ACCESS read-only
			STATUS current
			DESCRIPTION
				"Description."
			::= { gponOnuSipPstnUserInfoEntry 1 }

		
		-- 1.3.6.1.4.1.34592.1.5.1.1.2.20.4.1.2
		gponOnuSipPstnUserHookState OBJECT-TYPE
			SYNTAX INTEGER
				{
				onhook(1),
				offhook(2)
				}
			MAX-ACCESS read-only
			STATUS current
			DESCRIPTION
				"Description."
			::= { gponOnuSipPstnUserInfoEntry 2 }

		
		-- 1.3.6.1.4.1.34592.1.5.1.1.2.20.4.1.3
		gponOnuSipPstnUserCodec OBJECT-TYPE
			SYNTAX DisplayString
			MAX-ACCESS read-only
			STATUS current
			DESCRIPTION
				"Description."
			::= { gponOnuSipPstnUserInfoEntry 3 }

		
		-- 1.3.6.1.4.1.34592.1.5.1.1.2.20.4.1.4
		gponOnuSipPstnUserServerStatus OBJECT-TYPE
			SYNTAX DisplayString
			MAX-ACCESS read-only
			STATUS current
			DESCRIPTION
				"Description."
			::= { gponOnuSipPstnUserInfoEntry 4 }

		
		-- 1.3.6.1.4.1.34592.1.5.1.1.2.20.4.1.5
		gponOnuSipPstnUserSessionType OBJECT-TYPE
			SYNTAX DisplayString
			MAX-ACCESS read-only
			STATUS current
			DESCRIPTION
				"Description."
			::= { gponOnuSipPstnUserInfoEntry 5 }

		
		-- 1.3.6.1.4.1.34592.1.5.1.1.2.21
		gponOnuCatvPortObjects OBJECT IDENTIFIER ::= { gponControlObjects 21 }

		
		-- 1.3.6.1.4.1.34592.1.5.1.1.2.21.1
		gponOnuCatvPortCfgTable OBJECT-TYPE
			SYNTAX SEQUENCE OF GponOnuCatvPortCfgEntry
			MAX-ACCESS not-accessible
			STATUS current
			DESCRIPTION
				"Description."
			::= { gponOnuCatvPortObjects 1 }

		
		-- 1.3.6.1.4.1.34592.1.5.1.1.2.21.1.1
		gponOnuCatvPortCfgEntry OBJECT-TYPE
			SYNTAX GponOnuCatvPortCfgEntry
			MAX-ACCESS not-accessible
			STATUS current
			DESCRIPTION
				"Description."
			INDEX { gponOltDeviceId, gponOltCardId, gponOltPortId, gponOnuId, gponOnuCatvPortId
				 }
			::= { gponOnuCatvPortCfgTable 1 }

		
		GponOnuCatvPortCfgEntry ::=
			SEQUENCE { 
				gponOnuCatvPortId
					Integer32,
				gponOnuCatvPortOperationalState
					GponSwitch,
				gponOnuCatvPortCfgOnuIndex
					Integer32,
				gponOnuCatvPortAttribute
					GponSwitch
			 }

		-- 1.3.6.1.4.1.34592.1.5.1.1.2.21.1.1.1
		gponOnuCatvPortId OBJECT-TYPE
			SYNTAX Integer32 (1..8)
			MAX-ACCESS not-accessible
			STATUS current
			DESCRIPTION
				"Description."
			::= { gponOnuCatvPortCfgEntry 1 }

		
		-- 1.3.6.1.4.1.34592.1.5.1.1.2.21.1.1.2
		gponOnuCatvPortOperationalState OBJECT-TYPE
			SYNTAX GponSwitch
			MAX-ACCESS read-write
			STATUS current
			DESCRIPTION
				"Description."
			::= { gponOnuCatvPortCfgEntry 2 }

		
		-- 1.3.6.1.4.1.34592.1.5.1.1.2.21.1.1.3
		gponOnuCatvPortCfgOnuIndex OBJECT-TYPE
			SYNTAX Integer32
			MAX-ACCESS read-only
			STATUS current
			DESCRIPTION
				"Description."
			::= { gponOnuCatvPortCfgEntry 3 }

		
		-- 1.3.6.1.4.1.34592.1.5.1.1.2.21.1.1.4
		gponOnuCatvPortAttribute OBJECT-TYPE
			SYNTAX GponSwitch
			MAX-ACCESS read-only
			STATUS current
			DESCRIPTION
				"Description."
			::= { gponOnuCatvPortCfgEntry 4 }

		
		-- 1.3.6.1.4.1.34592.1.5.1.1.4
		gponAlarmObjects OBJECT IDENTIFIER ::= { gponObjects 4 }

		
		-- 1.3.6.1.4.1.34592.1.5.1.1.4.1
		gponNotifications OBJECT IDENTIFIER ::= { gponAlarmObjects 1 }

		
		-- 1.3.6.1.4.1.34592.1.5.1.1.4.1.1
		gponAlarmNotification NOTIFICATION-TYPE
			OBJECTS { gponTrapId, gponTrapState, gponTrapOltPortId, gponTrapOnuId, gponTrapOnuSn, 
				gponTrapOnuPassword, gponTrapRogueOnuSn, gponTrapParameters }
			STATUS current
			DESCRIPTION 
				"Description."
			::= { gponNotifications 1 }

		
		-- 1.3.6.1.4.1.34592.1.5.1.1.4.6
		gponTrapObjects OBJECT IDENTIFIER ::= { gponAlarmObjects 6 }

		
		-- 1.3.6.1.4.1.34592.1.5.1.1.4.6.1
		gponTrapId OBJECT-TYPE
			SYNTAX INTEGER
			MAX-ACCESS read-only
			STATUS current
			DESCRIPTION
				"Description."
			::= { gponTrapObjects 1 }

		
		-- 1.3.6.1.4.1.34592.1.5.1.1.4.6.2
		gponTrapState OBJECT-TYPE
			SYNTAX INTEGER
				{
				none(0),
				report(1),
				clear(2)
				}
			MAX-ACCESS read-only
			STATUS current
			DESCRIPTION
				"Description."
			::= { gponTrapObjects 2 }

		
		-- 1.3.6.1.4.1.34592.1.5.1.1.4.6.3
		gponTrapParameters OBJECT-TYPE
			SYNTAX BITS
				{
				none(0),
				oltPortId(1),
				onuId(2),
				onuSn(3),
				password(4),
				rogueOnuSn(5)
				}
			MAX-ACCESS read-only
			STATUS current
			DESCRIPTION
				"Description."
			::= { gponTrapObjects 3 }

		
		-- 1.3.6.1.4.1.34592.1.5.1.1.4.6.4
		gponTrapOltPortId OBJECT-TYPE
			SYNTAX Integer32 (1..8 | 65535)
			MAX-ACCESS read-only
			STATUS current
			DESCRIPTION
				"Description."
			::= { gponTrapObjects 4 }

		
		-- 1.3.6.1.4.1.34592.1.5.1.1.4.6.5
		gponTrapOnuId OBJECT-TYPE
			SYNTAX Integer32 (1..128 | 65535)
			MAX-ACCESS read-only
			STATUS current
			DESCRIPTION
				"Description."
			::= { gponTrapObjects 5 }

		
		-- 1.3.6.1.4.1.34592.1.5.1.1.4.6.6
		gponTrapOnuSn OBJECT-TYPE
			SYNTAX DisplayString
			MAX-ACCESS read-only
			STATUS current
			DESCRIPTION
				"Description."
			::= { gponTrapObjects 6 }

		
		-- 1.3.6.1.4.1.34592.1.5.1.1.4.6.7
		gponTrapOnuPassword OBJECT-TYPE
			SYNTAX DisplayString
			MAX-ACCESS read-only
			STATUS current
			DESCRIPTION
				"Description."
			::= { gponTrapObjects 7 }

		
		-- 1.3.6.1.4.1.34592.1.5.1.1.4.6.8
		gponTrapRogueOnuSn OBJECT-TYPE
			SYNTAX DisplayString
			MAX-ACCESS read-only
			STATUS current
			DESCRIPTION
				"Description."
			::= { gponTrapObjects 8 }

		
		-- 1.3.6.1.4.1.34592.1.5.1.1.4.8
		gponManagementObjects OBJECT IDENTIFIER ::= { gponAlarmObjects 8 }

		
		-- 1.3.6.1.4.1.34592.1.5.1.1.4.8.1
		gponManagementAddrTable OBJECT-TYPE
			SYNTAX SEQUENCE OF GponManagementAddrEntry
			MAX-ACCESS not-accessible
			STATUS current
			DESCRIPTION
				"Description."
			::= { gponManagementObjects 1 }

		
		-- 1.3.6.1.4.1.34592.1.5.1.1.4.8.1.1
		gponManagementAddrEntry OBJECT-TYPE
			SYNTAX GponManagementAddrEntry
			MAX-ACCESS not-accessible
			STATUS current
			DESCRIPTION
				"Description."
			INDEX { gponManagementAddrName }
			::= { gponManagementAddrTable 1 }

		
		GponManagementAddrEntry ::=
			SEQUENCE { 
				gponManagementAddrName
					OCTET STRING,
				gponManagementAddrRowStatus
					RowStatus,
				gponManagementAddrTAddress
					OCTET STRING,
				gponManagementAddrCommunity
					OCTET STRING
			 }

		-- 1.3.6.1.4.1.34592.1.5.1.1.4.8.1.1.1
		gponManagementAddrName OBJECT-TYPE
			SYNTAX OCTET STRING (SIZE (1..32))
			MAX-ACCESS not-accessible
			STATUS current
			DESCRIPTION
				"Description."
			::= { gponManagementAddrEntry 1 }

		
		-- 1.3.6.1.4.1.34592.1.5.1.1.4.8.1.1.2
		gponManagementAddrRowStatus OBJECT-TYPE
			SYNTAX RowStatus
			MAX-ACCESS read-create
			STATUS current
			DESCRIPTION
				"Description."
			::= { gponManagementAddrEntry 2 }

		
		-- 1.3.6.1.4.1.34592.1.5.1.1.4.8.1.1.3
		gponManagementAddrTAddress OBJECT-TYPE
			SYNTAX OCTET STRING (SIZE (8))
			MAX-ACCESS read-create
			STATUS current
			DESCRIPTION
				"Description."
			::= { gponManagementAddrEntry 3 }

		
		-- 1.3.6.1.4.1.34592.1.5.1.1.4.8.1.1.4
		gponManagementAddrCommunity OBJECT-TYPE
			SYNTAX OCTET STRING (SIZE (0..64))
			MAX-ACCESS read-create
			STATUS current
			DESCRIPTION
				"Description."
			::= { gponManagementAddrEntry 4 }

		
		-- 1.3.6.1.4.1.34592.1.5.1.1.4.9
		gponPortTrapManagementObjects OBJECT IDENTIFIER ::= { gponAlarmObjects 9 }

		
		-- 1.3.6.1.4.1.34592.1.5.1.1.4.9.1
		gponPortTrapAlarmTable OBJECT-TYPE
			SYNTAX SEQUENCE OF GponPortTrapAlarmEntry
			MAX-ACCESS not-accessible
			STATUS current
			DESCRIPTION
				"Description."
			::= { gponPortTrapManagementObjects 1 }

		
		-- 1.3.6.1.4.1.34592.1.5.1.1.4.9.1.1
		gponPortTrapAlarmEntry OBJECT-TYPE
			SYNTAX GponPortTrapAlarmEntry
			MAX-ACCESS not-accessible
			STATUS current
			DESCRIPTION
				"Description."
			INDEX { gponOltDeviceId, gponOltCardId, gponOltPortId, gponPortTrapAlarmId }
			::= { gponPortTrapAlarmTable 1 }

		
		GponPortTrapAlarmEntry ::=
			SEQUENCE { 
				gponPortTrapAlarmId
					Integer32,
				gponPortTrapAlarmStatus
					INTEGER
			 }

		-- 1.3.6.1.4.1.34592.1.5.1.1.4.9.1.1.2
		gponPortTrapAlarmId OBJECT-TYPE
			SYNTAX Integer32
			MAX-ACCESS read-write
			STATUS current
			DESCRIPTION
				"Description."
			::= { gponPortTrapAlarmEntry 2 }

		
		-- 1.3.6.1.4.1.34592.1.5.1.1.4.9.1.1.4
		gponPortTrapAlarmStatus OBJECT-TYPE
			SYNTAX INTEGER
				{
				disable(0),
				enable(1)
				}
			MAX-ACCESS read-write
			STATUS current
			DESCRIPTION
				"Description."
			::= { gponPortTrapAlarmEntry 4 }

		
		-- 1.3.6.1.4.1.34592.1.5.1.1.4.9.2
		gponPortTrapEventTable OBJECT-TYPE
			SYNTAX SEQUENCE OF GponPortTrapEventEntry
			MAX-ACCESS not-accessible
			STATUS current
			DESCRIPTION
				"Description."
			::= { gponPortTrapManagementObjects 2 }

		
		-- 1.3.6.1.4.1.34592.1.5.1.1.4.9.2.1
		gponPortTrapEventEntry OBJECT-TYPE
			SYNTAX GponPortTrapEventEntry
			MAX-ACCESS not-accessible
			STATUS current
			DESCRIPTION
				"Description."
			INDEX { gponOltDeviceId, gponOltCardId, gponOltPortId, gponPortTrapEventId }
			::= { gponPortTrapEventTable 1 }

		
		GponPortTrapEventEntry ::=
			SEQUENCE { 
				gponPortTrapEventId
					Integer32,
				gponPortTrapEventStatus
					INTEGER
			 }

		-- 1.3.6.1.4.1.34592.1.5.1.1.4.9.2.1.1
		gponPortTrapEventId OBJECT-TYPE
			SYNTAX Integer32
			MAX-ACCESS read-write
			STATUS current
			DESCRIPTION
				"Description."
			::= { gponPortTrapEventEntry 1 }

		
		-- 1.3.6.1.4.1.34592.1.5.1.1.4.9.2.1.2
		gponPortTrapEventStatus OBJECT-TYPE
			SYNTAX INTEGER
				{
				disable(0),
				enable(1)
				}
			MAX-ACCESS read-write
			STATUS current
			DESCRIPTION
				"Description."
			::= { gponPortTrapEventEntry 2 }

		
		-- 1.3.6.1.4.1.34592.1.5.1.1.64
		gponConformance OBJECT IDENTIFIER ::= { gponObjects 64 }

		
		-- 1.3.6.1.4.1.34592.1.5.1.1.64.1
		gponCompliances OBJECT IDENTIFIER ::= { gponConformance 1 }

		
		-- 1.3.6.1.4.1.34592.1.5.1.1.64.1.1
		gponCompliance MODULE-COMPLIANCE
			STATUS current
			DESCRIPTION 
				"Description."
			MODULE -- this module
				MANDATORY-GROUPS { gponDbaProfileGroup, gponLineProfileGroup, gponSrvProfileGroup, gponTrafficProfileGroup, gponSipAgentProfileGroup, 
					gponSipRightFlagProfileGroup, gponDigitMapProfileGroup, gponPotsProfileGroup }
			::= { gponCompliances 1 }

		
		-- 1.3.6.1.4.1.34592.1.5.1.1.64.2
		gponGroups OBJECT IDENTIFIER ::= { gponConformance 2 }

		
		-- 1.3.6.1.4.1.34592.1.5.1.1.64.2.1
		gponProfileGroups OBJECT IDENTIFIER ::= { gponGroups 1 }

		
		-- 1.3.6.1.4.1.34592.1.5.1.1.64.2.1.1
		gponDbaProfileGroup OBJECT-GROUP
			OBJECTS { gponDbaProfileFixRate, gponDbaProfileBindNum, gponDbaProfileName, gponDbaProfileRowStatus, gponDbaProfileMaxRate, 
				gponDbaProfileType, gponDbaProfileAssureRate }
			STATUS current
			DESCRIPTION 
				"Description."
			::= { gponProfileGroups 1 }

		
		-- 1.3.6.1.4.1.34592.1.5.1.1.64.2.1.2
		gponLineProfileGroup OBJECT-GROUP
			OBJECTS { gponLineProfileRowStatus, gponLineProfileName, gponLineProfileMappingMode, gponLineProfileTcontNum, gponLineProfileGemNum, 
				gponLineProfileBindNum, gponLineProfileTcontId, gponLineProfileTcontRowStatus, gponLineProfileTcontDbaProfileId, gponLineProfileGemId, 
				gponLineProfileGemRowStatus, gponLineProfileGemTcontId, gponLineProfileGemUpCar, gponLineProfileGemDownCar, gponLineProfileGemMapNum, 
				gponLineProfileGemMapId, gponLineProfileGemMapRowStatus, gponLineProfileGemMapPriority, gponLineProfileGemMapVlan }
			STATUS current
			DESCRIPTION 
				"Description."
			::= { gponProfileGroups 2 }

		
		-- 1.3.6.1.4.1.34592.1.5.1.1.64.2.1.3
		gponSrvProfileGroup OBJECT-GROUP
			OBJECTS { gponSrvProfileId, gponSrvProfileRowStatus, gponSrvProfileName, gponSrvProfileBindNum, gponSrvProfileMcMode, 
				gponSrvProfileUpIgmpFwdMode, gponSrvProfileUpIgmpTCI, gponSrvProfileDnMcMode, gponSrvProfileDnMcTCI, gponSrvProfileEthNum, 
				gponSrvProfilePotsNum, gponSrvProfileOntPortType, gponSrvProfileOntPortId, gponSrvProfileOntPortCvlan, gponSrvProfileOntPortVlanRowStatus, 
				gponSrvProfileOntPortVlanMode, gponSrvProfileOntPortVlanSvlan }
			STATUS current
			DESCRIPTION 
				"Description."
			::= { gponProfileGroups 3 }

		
		-- 1.3.6.1.4.1.34592.1.5.1.1.64.2.1.4
		gponTrafficProfileGroup OBJECT-GROUP
			OBJECTS { gponTrafficProfileId, gponTrafficProfileRowStatus, gponTrafficProfileName, gponTrafficProfileBindNum, gponTrafficProfileCfgCir, 
				gponTrafficProfileCfgPir, gponTrafficProfileCfgCbs, gponTrafficProfileCfgPbs }
			STATUS current
			DESCRIPTION 
				"Description."
			::= { gponProfileGroups 4 }

		
		-- 1.3.6.1.4.1.34592.1.5.1.1.64.2.1.5
		gponSipAgentProfileGroup OBJECT-GROUP
			OBJECTS { gponSipAgentProfileRowStatus, gponSipAgentProfileName, gponSipAgentProfileBindNum, gponSipAgentProfileProxyServerUri, gponSipAgentProfileRtpDscp, 
				gponSipAgentProfileRtpMinPort, gponSipAgentProfileRtpMaxPort, gponSipAgentProfileSignalDscp, gponSipAgentProfileSignalPort, gponSipAgentProfileSignalTransferMode, 
				gponSipAgentProfileRegistrationExpiration, gponSipAgentProfileRegistrationReregHeadStartTime, gponSipAgentProfileRegistrationServerUri, gponSipAgentProfileVoiceMailServerUri, gponSipAgentProfileVoiceMailSubscriptionExpiration, 
				gponSipAgentProfileConfFactory, gponSipAgentProfileBridgedLineAgent, gponSipAgentProfileAuthRealm, gponSipAgentProfileBindPotsList }
			STATUS current
			DESCRIPTION 
				"Description."
			::= { gponProfileGroups 5 }

		
		-- 1.3.6.1.4.1.34592.1.5.1.1.64.2.1.6
		gponSipRightFlagProfileGroup OBJECT-GROUP
			OBJECTS { gponSipRightFlagProfileId, gponSipRightFlagProfileRowStatus, gponSipRightFlagProfileName, gponSipRightFlagProfileBindNum, gponSipRightFlagProfileCallWaiting, 
				gponSipRightFlagProfileCallProcess, gponSipRightFlagProfileCallPresentation, gponSipRightFlagProfileHotline, gponSipRightFlagProfileHotlineNum, gponSipRightFlagProfileBindPotsList
				 }
			STATUS current
			DESCRIPTION 
				"Description."
			::= { gponProfileGroups 6 }

		
		-- 1.3.6.1.4.1.34592.1.5.1.1.64.2.1.7
		gponDigitMapProfileGroup OBJECT-GROUP
			OBJECTS { gponDigitMapProfileId, gponDigitMapProfileRowStatus, gponDigitMapProfileName, gponDigitMapProfileBindNum, gponDigitMapProfileCriticalDialTime, 
				gponDigitMapProfileDialPlanId, gponDigitMapProfileDialPlanRowStatus, gponDigitMapProfileDialPlanToken, gponDigitMapProfileBindPotsList }
			STATUS current
			DESCRIPTION 
				"Description."
			::= { gponProfileGroups 7 }

		
		-- 1.3.6.1.4.1.34592.1.5.1.1.64.2.1.8
		gponPotsProfileGroup OBJECT-GROUP
			OBJECTS { gponPotsProfileId, gponPotsProfileRowStatus, gponPotsProfileName, gponPotsProfileBindNum, gponPotsProfileImpedance, 
				gponPotsProfileSignallingCode, gponPotsProfileRxGain, gponPotsProfileTxGain, gponPotsProfileBindPotsList }
			STATUS current
			DESCRIPTION 
				"Description."
			::= { gponProfileGroups 8 }

		
		-- 1.3.6.1.4.1.34592.1.5.1.1.64.2.2
		gponControlGroups OBJECT IDENTIFIER ::= { gponGroups 2 }

		
		-- 1.3.6.1.4.1.34592.1.5.1.1.64.2.2.1
		gponControlGroup OBJECT-GROUP
			OBJECTS { gponOltPortAutoFindSwitch, gponOltPortSwitch, gponOltPortStatus, gponOltPortDdmTemperature, gponOltPortDdmVoltage, 
				gponOltPortDdmTxBiasCurrent, gponOltPortDdmTxPower, gponOltPortDdmRxPower, gponOltTransceiverVendor, gponOltTransceiverProductName, 
				gponOltTransceiverVersion, gponOltTransceiverSerialNumber, gponOnuId, gponOnuRowStatus, gponOnuAuthMode, 
				gponOnuSn, gponOnuPassword, gponOnuLineProfileId, gponOnuServiceProfileId, gponOnuDescription, 
				gponOnuRunState, gponOnuConfigState, gponOnuMatchState, gponOnuDistance, gponOnuPonPortNum, 
				gponOnuEthPortNum, gponOnuPotsPortNum, gponOnuGemPortNum, gponOnuTcontNum, gponOnuFlowControlType, 
				gponOnuReset, gponOnuDeactive, gponOnuAutofindRowStatus, gponOnuAutofindSn, gponOnuAutofindPassword, 
				gponOnuAutofindVendorId, gponOnuAutofindVersion, gponOnuAutofindEquipmentID, gponOnuAutofindSoftwareVersion, gponOnuAutofindTime, 
				gponOnuOpticalVoltage, gponOnuOpticalTxPower, gponOnuOpticalRxPower, gponOnuOpticalLaserBiasCurrent, gponOnuOpticalTemperature, 
				gponOnuMainSoftwareVersion, gponOnuStandbySoftwareVersion, gponOnuEthPortId, gponOnuEthPortNativeVlanId, gponOnuEthPortNativeVlanPriority, 
				gponOnuEthPortInboundCarId, gponOnuEthPortOutboundCarId, gponOnuEthPortSpeedAndDuplex, gponOnuEthPortFlowCtrl, gponOnuEthPortOperationalState, 
				gponOnuEthPortSpeedAndDuplexInfo, gponOnuEthPortState, gponOnuEthPortMacAddressId, gponOnuEthPortMacAddress, gponOnuPotsPortId, 
				gponOnuPotsPortOperationalState, gponOnuPotsPortCfgPotsProfileId, gponOnuIpCfgRowStatus, gponOnuIpCfgMode, gponOnuIpCfgVlanId, 
				gponOnuIpCfgVlanPri, gponOnuIpCfgIp, gponOnuIpCfgMask, gponOnuIpCfgGateway, gponOnuIpCfgPriDns, 
				gponOnuIpCfgSlaveDns, gponOnuIpCfgMacAddress, gponOnuSipPstnUserRowStatus, gponOnuSipPstnUserName, gponOnuSipPstnUserPassword, 
				gponOnuSipPstnUserTelephoneNumber, gponOnuSipPstnUserAgentProfileId, gponOnuSipPstnUserDigitMapProfileId, gponOnuSipPstnUserSipRightFlagProfileId, gponOnuSipPstnUserState, 
				gponOnuSipPstnUserHookState, gponOnuSipPstnUserCodec, gponOnuSipPstnUserServerStatus, gponOnuSipPstnUserSessionType }
			STATUS current
			DESCRIPTION 
				"Description."
			::= { gponControlGroups 1 }

		
		-- 1.3.6.1.4.1.34592.1.5.1.1.64.2.4
		gponTrapGroups OBJECT IDENTIFIER ::= { gponGroups 4 }

		
		-- 1.3.6.1.4.1.34592.1.5.1.1.64.2.4.1
		gponTrapGroup OBJECT-GROUP
			OBJECTS { gponTrapOltPortId, gponTrapOnuId, gponTrapOnuSn }
			STATUS current
			DESCRIPTION 
				"Description."
			::= { gponTrapGroups 1 }

		
		-- 1.3.6.1.4.1.34592.1.5.1.1.64.2.4.2
		gponTrapTypeGroup NOTIFICATION-GROUP
			NOTIFICATIONS { gponAlarmNotification }
			STATUS current
			DESCRIPTION 
				"Description."
			::= { gponTrapGroups 2 }

		
	
	END

--
-- CDATA-GPON-MIB.my
--
