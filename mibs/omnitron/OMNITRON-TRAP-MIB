OMNITRON-TRAP-MIB DEFINITIONS ::= BEGIN

IMPORTS
    MODULE-IDENTITY, OBJECT-TYPE, NOTIFICATION-TYPE, IpAddress, Integer32, Unsigned32, Counter64
        FROM SNMPv2-SMI           -- RFC-2578
    DisplayString, DateAndTime
        FROM SNMPv2-TC            -- RFC-2579
    MODULE-COMPLIANCE, OBJECT-GROUP, NOTIFICATION-GROUP
        FROM SNMPv2-CONF          -- RFC-2580
    dsx1LineStatus, dsx1LineStatusLastChange
        FROM DS1-MIB              -- RFC-4805
    mefSoamAisStatsInStatus, mefSoamAisStatsOutStatus, mefSoamLckStatsInStatus, mefSoamLckStatsOutStatus
        FROM MEF-SOAM-FM-MIB      -- MEF SOAM FM MIB
    omnitron, OstModeType, icAgent, OstPortClockType, OstIpAddr, OstErpsRingStatus
        FROM OMNITRON-TC-MIB;     -- Omnitron Textual Convention MIB

omnitronTrapMIB MODULE-IDENTITY
    LAST-UPDATED "201706271200Z"  -- June 27, 2017
    ORGANIZATION "Omnitron Systems Technology, Inc."
    CONTACT-INFO "Omnitron Systems Technology, Inc.
                  38 Tesla
                  Irvine, CA 92618-4670
                  USA

             Tel: (949) 250 6510
             Fax: (949) 250 6514
          E-mail: info@omnitron-systems.com
   International: +1 949 250 6510

                  Technical Support and Customer Service
             Tel: (800) 675 8410
          E-mail: support@omnitron-systems.com
   International: +1 949 250 6510"

    DESCRIPTION
            "Omnitron Trap MIB for use with v5.3 iConverter Management Modules
             and NetOutlook

             Copyright 2017 Omnitron Systems Technology, Inc.
             All rights reserved
            "

    REVISION    "201706271200Z"  -- June 27, 2017
    DESCRIPTION "Updated description of trapip and trapIpString
                "

    REVISION    "201701181200Z"     -- January 18, 2017
    DESCRIPTION "Modified icRingProtectStateChange trap TLV order
                "

    REVISION    "201701091200Z"  -- January 9, 2017
    DESCRIPTION "Added icAuthTelnetFail trap 
                 Added icRingProtectStateChange trap
                 Added eventProtectState
                "

    REVISION    "201604081200Z"     -- April 8, 2016
    DESCRIPTION "Added trapip back into the trap object list
                 Added eventSrcIp back into the trap object list
                "
                
    REVISION    "201603181200Z"  -- March 18, 2016
    DESCRIPTION "Initial version of v5.3 MIB:
                     Added eventSrcIpString, deprecated eventSrcIp
                     Added trapIpString, deprecated trapip
                "
    ::= { omnitron 12 }

omnitronNotifications       OBJECT IDENTIFIER ::= { omnitron 0 }  -- 0 required for reverse mapping to SNMPv1
omnitronNotificationObjects OBJECT IDENTIFIER ::= { omnitron 6 }

ostTrapObjects              OBJECT IDENTIFIER ::= { omnitronTrapMIB 1 }
ostTrapConformance          OBJECT IDENTIFIER ::= { omnitronTrapMIB 2 }


-- *****************************************************************************
-- Trap Configuration Table
-- *****************************************************************************

ostTrapCfgTable OBJECT-TYPE
    SYNTAX      SEQUENCE OF OstTrapCfgEntry
    MAX-ACCESS  not-accessible
    STATUS      current
    DESCRIPTION
       "This table supports the configuration and source filtering of SNMP
        notifications generated by Omnitron management modules."
    ::= { ostTrapObjects 1 }

ostTrapCfgEntry OBJECT-TYPE
    SYNTAX      OstTrapCfgEntry
    MAX-ACCESS  not-accessible
    STATUS      current
    DESCRIPTION
       "This is a Trap Filtering configuration table entry."
    INDEX { ostTrapCfgTrapCode }
    ::= { ostTrapCfgTable 1 }

OstTrapCfgEntry ::= SEQUENCE {
    ostTrapCfgTrapCode                      Unsigned32,
    ostTrapCfgFilteringEnable               INTEGER,
    ostTrapCfgStatus                        INTEGER,
    ostTrapCfgSeverity                      INTEGER
    }

ostTrapCfgTrapCode OBJECT-TYPE
    SYNTAX      Unsigned32
    MAX-ACCESS  not-accessible
    STATUS      current
    DESCRIPTION
       "An index to the Trap Configuration table. The entry (index) corresponds
        to the 'trapcode' object indicating a specific trap code for an SNMP
        notification.

        Standard Omnitron traps are listed as 1 through 9999
        CFM standard MIB specific traps are listed as 10001-10099
        DS1 standard MIB specific traps are listed as 10100-10199
        MEF standard MIB specific traps are listed as 10200-10299
        LLDP standard MIB specific traps are listed as 10300-10399
        SNMPv2 standard MIB specific traps are listed as 10400-10499
        ENTITY standard MIB specific traps are listed as 10500-10599
        BRIDGE standard MIB specific traps are listed as 10600-10699
        RMON standard MIB specific traps are listed as 10700-10799

        Rows are automatically created based upon which notifications can be
        configured by the user.
       "
    ::= { ostTrapCfgEntry 1 }

ostTrapCfgFilteringEnable OBJECT-TYPE
    SYNTAX      INTEGER {
        noFiltering (1),
        filtering(2)
    }
    MAX-ACCESS  read-write
    STATUS      current
    DESCRIPTION
       "This object selects whether the notification indicated by the
        ostTrapFilteringTrapCode object is filtered or is generated when
        the specific condition is encountered.

        noFiltering (1)   Notification is generated when condition is met
        filtering(2)      Notification is generated when condition is met

        This object can be read or written at any time.
       "
    DEFVAL { 1 }
    ::= { ostTrapCfgEntry 2 }

ostTrapCfgStatus OBJECT-TYPE
    SYNTAX      INTEGER {
        trapNotActive(1),
        trapActive(2)
    }
    MAX-ACCESS  read-write
    STATUS      current
    DESCRIPTION
       "*** NOT SUPPORTED ***
        This object has been deprecated.
       "
    ::= { ostTrapCfgEntry 3 }

ostTrapCfgSeverity OBJECT-TYPE
    SYNTAX      INTEGER {
        trapSeverityInformation(1),
        trapSeverityWarning(2),
        trapSeverityMinor(3),
        trapSeverityMajor(4),
        trapSeverityCritical(5)
    }
    MAX-ACCESS  read-write
    STATUS      current
    DESCRIPTION
       "This object indicates the severity configuration of a SNMP trap. Each
        trap is able to have a separate severity configuration.

        trapSeverityInformation(1)   Trap is of informational severity only and
                                     is non-service affecting
        trapSeverityWarning(2),      Trap is of warning severity and indicates
                                     a potential service affecting event
        trapSeverityMinor(3),        Trap is of minor severity and indicates a
                                     non-service affecting event
        trapSeverityMajor(4),        Trap is of major severity and indicates a
                                     service-affecting event and urgent
                                     corrective action is required
        trapSeverityCritical(5)      Trap is of critical severity and indicates
                                     a service-affecting event and immediate
                                     corrective action is required

        This object can read or written at any time.
       "
    DEFVAL { trapSeverityInformation }
    ::= { ostTrapCfgEntry 4 }


ostTrapCfgSetClearAll OBJECT-TYPE
    SYNTAX      INTEGER {
        setAllTrapsNoFilters(1),
        setAllTrapsFilter(2)
    }
    MAX-ACCESS  read-write
    STATUS      current
    DESCRIPTION
       "This object when written performs the configured options for all
        possible SNMP traps.


        When object is written:
        setAllTrapsNoFilters(1)  All traps are configured to not filtered,
                                 meaning the product can generate all traps.

        setAllTrapsFilter(2)     All traps are configured to filtered,
                                 meaning the product cannot generate any trap.

        This object can read or written at any time.
       "
    DEFVAL { 1 }
    ::= { ostTrapObjects 2 }


ostTrapCfgSeverityLevelReporting    OBJECT-TYPE
    SYNTAX      BITS {
                     bInformation(0),
                     bWarning(1),
                     bMinor(2),
                     bMajor(3),
                     bCritical(4)
                }
    MAX-ACCESS  read-write
    STATUS      current
    DESCRIPTION
       "A vector of bits that sets which notifications (SNMP traps) are
        generated based upon its severity level.

        Each SNMP trap has a severity level configuration. This object
        configures which trap severity levels are generated (reported).
        In general it is a threshold indicator. If all SNMP traps Major
        and higher are to be generated then the Major and Critical bits would
        be set. Since this object is a bit vector any individual severity can
        be set independently of other severity levels.

        A bit set to '1' indicates the specific severity level will generate
        an SNMP traps. A bit set to '0' indicates the specific severity level
        will not generate an SNMP trap.


        bInformation(0)      Enable for traps with severity level set to
                             Information
        bWarning(1)          Enable for traps with severity level set to
                             Warning

        bMinor(2)            Enable for traps with severity level set to
                             Minor

        bMajor(3)            Enable for traps with severity level set to
                             Major

        bCritical(4)         Enable for traps with severity level set to
                             Critical
      "
    DEFVAL { { bInformation,bWarning,bMinor,bMajor,bCritical } }
    ::= { ostTrapObjects 6 }


-- *****************************************************************************
-- Alarm Status Table
-- *****************************************************************************

ostAlarmStatusTable OBJECT-TYPE
    SYNTAX      SEQUENCE OF OstAlarmStatusEntry
    MAX-ACCESS  not-accessible
    STATUS      current
    DESCRIPTION
       "This table supports the status of alarms generated by Omnitron
        management modules.
       "
    ::= { ostTrapObjects 3 }

ostAlarmStatusEntry OBJECT-TYPE
    SYNTAX      OstAlarmStatusEntry
    MAX-ACCESS  not-accessible
    STATUS      current
    DESCRIPTION
       "This the Alarm Status table entry."
    INDEX { ostAlarmStatusIndex }
    ::= { ostAlarmStatusTable 1 }

OstAlarmStatusEntry ::= SEQUENCE {
    ostAlarmStatusIndex                    Unsigned32,
    ostAlarmStatusIdentifier               Unsigned32,
    ostAlarmStatusInstance                 OCTET STRING,
    ostAlarmStatusTime                     DateAndTime,
    ostAlarmStatusDescription              DisplayString
    }

ostAlarmStatusIndex OBJECT-TYPE
    SYNTAX      Unsigned32
    MAX-ACCESS  not-accessible
    STATUS      current
    DESCRIPTION
       "An index to the Alarm Status table.

        Alarm Status table indices are assigned sequentially by the SNMP
        Agent. When initialized the starting index number is 1.

        An entry is added to the table dynamically at the next sequentially
        available index number when an alarm becomes active. When an alarm
        is cleared the row is automatically deleted from the table. This
        indicates that only active alarms are present in the table.

        Referential integrity is necessary, i.e., the index needs to be
        persistent upon a reboot or restart of a device.  The index
        is never reused for a new alarm entry until the index wraps to zero.
        The index value keeps increasing up to that time.
       "
    ::= { ostAlarmStatusEntry 1 }

ostAlarmStatusIdentifier OBJECT-TYPE
    SYNTAX      Unsigned32
    MAX-ACCESS  read-only
    STATUS      current
    DESCRIPTION
       "The specific alarm number. This object can take one of the following
        values:

        Number   Alarm Description
        ------   ---------------------------
        1        Module Lost
        2        Link Down
        3        Temperature
        4        Voltage out of range
        5        Power removed
        6        Chassis Gone
        7        Redundant Fault
        8        Telnet Session Started
        9        FTP Session Started
        10       TDM Data
        11       Mastership Lost
        12       SFP Removal
        13       Remote Link Fault
        14       Local Link Fault
        15       Remote Loopback
        16       MEP Error
        17       SFP/XFP Error
        18       Local Loopback
        19       Remote Unit Found
        20       Remote Error
        21       Clock Error
        22       Serial Session Started
        23       Remote Test Active
        24       Local Test Active
        25       SSH Session Started
        26       Fan
        27       1588 Sync
        28       SyncE
        29       OAM AIS
        30       OAM LCK
        31       Threshold Crossing
        32       SFP/XFP Receive CDR
        33       SFP/XFP Transmit CDR
        34       DPoE Stage Warning
        35       DPoE Stage Failure
        36       PoE PD Status
        37       Link OAM Discovery Lost
        38       Service Activation Test In Process
        39       Utilization Threshold Violation
        40       Loop Prevention Block
       "
    ::= { ostAlarmStatusEntry 2 }

ostAlarmStatusInstance OBJECT-TYPE
    SYNTAX      OCTET STRING (SIZE(0..64))
    MAX-ACCESS  read-write
    STATUS      current
    DESCRIPTION
       "The specific alarm unique instance number. This object can take one
        of the following octet formats dependent upon the scope of the alarm:

        Scope          Format
        --------       ------
        module         'Chassis cc Slot ss Port pp'
        port           'Chassis cc Slot ss Port pp' for plug-ins
                       'Port pp' for standalone modules
        power          'Chassis cc Slot ss Port pp' for plug-ins
                       'Port pp' for standalone modules
        chassis        'Chassis cc'
        md/ma/mep      'MD mmmm MA aaaa MEP mmmm'
        threshold      'MD mmmm MA aaaa MEP mmmm Threshold tttt'
        instance       'xxxx'

        Writing any value into this object clears the specific alarm and
        removes it from the Alarm Table.
       "
    ::= { ostAlarmStatusEntry 3 }

ostAlarmStatusTime OBJECT-TYPE
    SYNTAX      DateAndTime
    MAX-ACCESS  read-only
    STATUS      current
    DESCRIPTION
       "The time when the alarm was added to the Alarm Table.
       "
    ::= { ostAlarmStatusEntry 4 }

ostAlarmStatusDescription OBJECT-TYPE
    SYNTAX      DisplayString (SIZE(0..64))
    MAX-ACCESS  read-only
    STATUS      current
    DESCRIPTION
       "The description of the specific alarm."
    ::= { ostAlarmStatusEntry 5 }


ostAlarmStatusClearAll OBJECT-TYPE
    SYNTAX      Unsigned32
    MAX-ACCESS  read-write
    STATUS      current
    DESCRIPTION
       "This object when written with any value causes the alarm table
        to be cleared.
       "
    ::= { ostTrapObjects 4 }


-- *****************************************************************************
-- Alarm History Table
-- *****************************************************************************

ostAlarmHistoryTable OBJECT-TYPE
    SYNTAX      SEQUENCE OF OstAlarmHistoryEntry
    MAX-ACCESS  not-accessible
    STATUS      current
    DESCRIPTION
       "This table supports the history of cleared alarms generated by Omnitron
        management modules.
       "
    ::= { ostTrapObjects 5 }

ostAlarmHistoryEntry OBJECT-TYPE
    SYNTAX      OstAlarmHistoryEntry
    MAX-ACCESS  not-accessible
    STATUS      current
    DESCRIPTION
       "This the Alarm Historytable entry."
    INDEX { ostAlarmHistoryIndex }
    ::= { ostAlarmHistoryTable 1 }

OstAlarmHistoryEntry ::= SEQUENCE {
    ostAlarmHistoryIndex                    Unsigned32,
    ostAlarmHistoryIdentifier               Unsigned32,
    ostAlarmHistoryInstance                 OCTET STRING,
    ostAlarmHistoryStartTime                DateAndTime,
    ostAlarmHistoryEndTime                  DateAndTime,
    ostAlarmHistoryDescription              DisplayString
    }

ostAlarmHistoryIndex OBJECT-TYPE
    SYNTAX      Unsigned32
    MAX-ACCESS  not-accessible
    STATUS      current
    DESCRIPTION
       "An index to the Alarm History table.

        Alarm History table indices are assigned sequentially by the SNMP
        Agent. When initialized the starting index number is 1.

        An entry is added to the table dynamically at the next sequentially
        available index number when an alarm becomes inactive. The last 100
        alarms are stored in the table. Alarms older than the last 100 are
        automatically deleted.

        Referential integrity is necessary, i.e., the index needs to be
        persistent upon a reboot or restart of a device.  The index
        is never reused for a new alarm entry until the index wraps to zero.
        The index value keeps increasing up to that time.
       "
    ::= { ostAlarmHistoryEntry 1 }

ostAlarmHistoryIdentifier OBJECT-TYPE
    SYNTAX      Unsigned32
    MAX-ACCESS  read-only
    STATUS      current
    DESCRIPTION
       "The specific alarm number. This object can take one of the values
       defined by the ostAlarmStatusIdentifier object.
       "
    ::= { ostAlarmHistoryEntry 2 }

ostAlarmHistoryInstance OBJECT-TYPE
    SYNTAX     OCTET STRING (SIZE(0..64))
    MAX-ACCESS  read-only
    STATUS      current
    DESCRIPTION
       "The specific alarm unique instance number. This object takes one of
        the formats defined by the ostAlarmStatusInstance object.
       "
    ::= { ostAlarmHistoryEntry 3 }

ostAlarmHistoryStartTime OBJECT-TYPE
    SYNTAX      DateAndTime
    MAX-ACCESS  read-only
    STATUS      current
    DESCRIPTION
       "The time when the alarm was added to the Alarm Status Table.
       "
    ::= { ostAlarmHistoryEntry 4 }

ostAlarmHistoryEndTime OBJECT-TYPE
    SYNTAX      DateAndTime
    MAX-ACCESS  read-only
    STATUS      current
    DESCRIPTION
       "The time when the alarm was removed from the Alarm Status Table.
       "
    ::= { ostAlarmHistoryEntry 5 }

ostAlarmHistoryDescription OBJECT-TYPE
    SYNTAX      DisplayString (SIZE(0..64))
    MAX-ACCESS  read-only
    STATUS      current
    DESCRIPTION
       "The description of the specific alarm."
    ::= { ostAlarmHistoryEntry 6 }



-- *****************************************************************************
-- Enterprise Specific Trap Objects
-- *****************************************************************************

trapchassis OBJECT-TYPE
    SYNTAX      Integer32 (1..19)
    MAX-ACCESS  accessible-for-notify
    STATUS      current
    DESCRIPTION
       "Chassis number of module that generated the trap"
    ::= { icAgent 2 }

trapslot    OBJECT-TYPE
    SYNTAX      Integer32 (1..22)
    MAX-ACCESS  accessible-for-notify
    STATUS      current
    DESCRIPTION
       "Slot number of module that generated the trap"
    ::= { icAgent 3 }

trapcode    OBJECT-TYPE
    SYNTAX      Integer32 (0..255)
    MAX-ACCESS  accessible-for-notify
    STATUS      current
    DESCRIPTION
       "Type of extended trap"
    ::= { icAgent 4 }

trapip    OBJECT-TYPE
    SYNTAX      IpAddress
    MAX-ACCESS  accessible-for-notify
    STATUS      current
    DESCRIPTION
       "IPv4 address of the trap source. If an IPv6 address is configured the 
        return value is either 0.0.0.0 or 255.255.255.255.
       "
    ::= { icAgent 5 }

trapmoduledescription  OBJECT-TYPE
    SYNTAX      DisplayString (SIZE(0..64))
    MAX-ACCESS  accessible-for-notify
    STATUS      current
    DESCRIPTION
       "The module description"
    ::= { icAgent 7 }

trapmodetype    OBJECT-TYPE
    SYNTAX      OstModeType
    MAX-ACCESS  accessible-for-notify
    STATUS      current
    DESCRIPTION
      "The module Mode Type"
    ::= { icAgent 9 }

trapIpString    OBJECT-TYPE
    SYNTAX      OstIpAddr
    MAX-ACCESS  accessible-for-notify
    STATUS      current
    DESCRIPTION
       "IPv6 or IPv4 address of the trap source. If no address is configured the
        value returned is 0.0.0.0 or 255.255.255.255."
    ::= { icAgent 10 }


-- *****************************************************************************
-- Notification Objects
-- *****************************************************************************

trapAgMdIndex OBJECT-TYPE
    SYNTAX      Unsigned32 (1..4294967295)
    MAX-ACCESS  accessible-for-notify
    STATUS      current
    DESCRIPTION
       "Holds the Maintenance Domain Index of the MEP generating the 802.1ag
        trap"
    ::= { omnitronNotificationObjects 1 }

trapAgMaIndex OBJECT-TYPE
    SYNTAX      Unsigned32 (1..4294967295)
    MAX-ACCESS  accessible-for-notify
    STATUS      current
    DESCRIPTION
      "Holds the Maintenance Association Index of the MEP generating the 802.1ag
       trap"
    ::= { omnitronNotificationObjects 2 }

trapAgMepId OBJECT-TYPE
    SYNTAX      Integer32 (1..8191)
    MAX-ACCESS  accessible-for-notify
    STATUS      current
    DESCRIPTION
       "Holds the MEPID value of the MEP generating the 802.1ag trap"
    ::= { omnitronNotificationObjects 3 }

trapAgErrorCode OBJECT-TYPE
    SYNTAX      Integer32
    MAX-ACCESS  accessible-for-notify
    STATUS      current
    DESCRIPTION
       "Holds the error code of the MEP generating the 802.1ag trap. This value
        is the same as dot1agCfmMepHighestPrDefect returned with the 802.1ag
        dot1agCfmFaultAlarm notification, see the ieee8021CfmMib module.
       "
    ::= { omnitronNotificationObjects 4 }


-- *****************************************************************************
-- Variables for event notification traps
-- *****************************************************************************

eventNotificationType           OBJECT-TYPE
    SYNTAX      Integer32 (1..4)
    MAX-ACCESS  accessible-for-notify
    STATUS      current
    DESCRIPTION
       "Holds the event notification type.
        Possible values are:
            0x01 - Errored Symbol Period
            0x02 - Errored Frame
            0x03 - Errored Frame Period
            0x04 - Errored Frame Seconds Summary
       "
    ::= { omnitronNotificationObjects 5 }

eventNotificationErrors         OBJECT-TYPE
    SYNTAX      Counter64
    MAX-ACCESS  accessible-for-notify
    STATUS      current
    DESCRIPTION
       "Holds the number of errors in the specified period"
    ::= { omnitronNotificationObjects 6 }

eventNotificationErrorTotal     OBJECT-TYPE
    SYNTAX      Counter64
    MAX-ACCESS  accessible-for-notify
    STATUS      current
    DESCRIPTION
       "Holds the sum of errors since OAM sublayer was reset"
    ::= { omnitronNotificationObjects 7 }

eventNotificationEventsTotal    OBJECT-TYPE
    SYNTAX      Counter64
    MAX-ACCESS  accessible-for-notify
    STATUS      current
    DESCRIPTION
       "Holds the number of events since reset"
    ::= { omnitronNotificationObjects 8 }

eventThresholdIdentification    OBJECT-TYPE
    SYNTAX      INTEGER {
        frameDelay(1),
        frameDelayVariation(2),
        frameLoss(3),
        availability(4)
    }
    MAX-ACCESS  accessible-for-notify
    STATUS      current
    DESCRIPTION
       "Holds the threshold identification value"
    ::= { omnitronNotificationObjects 9 }

eventPortClockState    OBJECT-TYPE
    SYNTAX      OstPortClockType
    MAX-ACCESS  accessible-for-notify
    STATUS      current
    DESCRIPTION
       "Holds the port clock state at the time of the notification"
    ::= { omnitronNotificationObjects 10 }

eventDpoeStageNumber    OBJECT-TYPE
    SYNTAX      Unsigned32 (1..5)
    MAX-ACCESS  accessible-for-notify
    STATUS      current
    DESCRIPTION
       "Holds the DPoE stage number at the time of the notification"
    ::= { omnitronNotificationObjects 11 }

eventSetClear  OBJECT-TYPE
    SYNTAX      INTEGER {
        alarmSet    (1),
        alarmClear  (2)
    }
    MAX-ACCESS  accessible-for-notify
    STATUS      current
    DESCRIPTION
       "Holds the alarm status at the time of the notification

        alarmSet(1)    Alarm is active or set
        alarmClear(2)  Alarm is not active or cleared
       "
    ::= { omnitronNotificationObjects 12 }


eventPdStatus    OBJECT-TYPE
    SYNTAX      BITS {
                     bNoPdDetected(0),
                     bIllegalClassification(1),
                     bOverCurrent(2),
                     bBrownOut(3),
                     bInsufficientPower(4),
                     bHeartbeatLost(5)
                }
    MAX-ACCESS  accessible-for-notify
    STATUS      current
    DESCRIPTION
       "A vector of bits that indicates the PoE PD Status

        A bit set to '1' indicates the specific errored condition. A bit set to
        '0' indicates the specific errored condition is not present


        bNoPdDetected(0)            No PD device found for a PSE enabled port

        bIllegalClassification(1)   PD device classification is illegal or
                                    unrecognized

        bOverCurrent(2)             PD device requesting more power than
                                    was determined during classification

        bBrownOut(3)                PD device are experiencing brown-out since
                                    PSE cannot source requested power

        bInsufficientPower(4)       PD device is not powered since power
                                    classification cannot be met

        bHeartbeatLost(5)           PD device with heartbeat enabled is not
                                    responding with heartbeat
      "
    ::= { omnitronNotificationObjects 13 }

contactClosureStatus    OBJECT-TYPE
    SYNTAX      INTEGER {
        contactOpen(1),
        contactClosed(2)
    }
    MAX-ACCESS  accessible-for-notify
    STATUS      current
    DESCRIPTION
       "Holds the contact closure status at the time of the notification

        contactOpen(1)   Contact closure is open
        contactClosed(2) Contact closure is closed
       "
    ::= { omnitronNotificationObjects 14 }

eventSrcIp OBJECT-TYPE
    SYNTAX      IpAddress
    MAX-ACCESS  accessible-for-notify
    STATUS      current
    DESCRIPTION
       "Originating IPv4 address of the cause of the event. This object indicates
        the IP address of the cause of the error condition. For instance this
        object indicates the IP address of the originating IP address that
        caused an authentication error. It is distinct from 'trapip' object
        which indicates Omnitron product that is sending an event to the
        trap host.
        
        This object is not used and has been deprecated.
       "
    ::= { omnitronNotificationObjects 15 }

eventAclNumber OBJECT-TYPE
    SYNTAX      Unsigned32
    MAX-ACCESS  accessible-for-notify
    STATUS      current
    DESCRIPTION
       "ACL index number used to indicate which ACL was violated. A value of 0
        indicates the default value was violated. A non-zero value indicates
        the specific ostAclCfgIndex that caused the access violation.
       "
    ::= { omnitronNotificationObjects 16 }

eventProbePriorityNew OBJECT-TYPE
    SYNTAX      Unsigned32 (0..255)
    MAX-ACCESS  accessible-for-notify
    STATUS      current
    DESCRIPTION
       "Indicates the new probe VLAN C-TAG and S-TAG PCP
        (priority field) at the time of the notification

        Bits 4..1 are the C-TAG (inner tag) PCP field
        Bits 8..5 are the S-TAG (outer tag) PCP field

        Bit 1 is LSB and Bit 8 is MSB.
       "
    ::= { omnitronNotificationObjects 17 }

eventProbePriorityOld OBJECT-TYPE
    SYNTAX      Unsigned32 (0..255)
    MAX-ACCESS  accessible-for-notify
    STATUS      current
    DESCRIPTION
       "Indicates the old probe VLAN C-TAG and S-TAG PCP
        (priority field) at the time of the notification

        Bits 4..1 are the C-TAG (inner tag) PCP field
        Bits 8..5 are the S-TAG (outer tag) PCP field

        Bit 1 is LSB and Bit 8 is MSB.
       "
    ::= { omnitronNotificationObjects 18 }

eventSrcIpString OBJECT-TYPE
    SYNTAX      OstIpAddr
    MAX-ACCESS  accessible-for-notify
    STATUS      current
    DESCRIPTION
       "Originating IPv6 address of the cause of the event. This 
        object indicates the IP address of the cause of the error condition.
        For instance this object indicates the IP address of the originating
        IP address that caused an authentication error. It is distinct from
        'trapIpString' object which indicates Omnitron product that is sending
        an event to the trap host.
       "
    ::= { omnitronNotificationObjects 19 }
    
eventProtectState OBJECT-TYPE
    SYNTAX      OstErpsRingStatus
    MAX-ACCESS  accessible-for-notify
    STATUS      current
    DESCRIPTION
       "Indicates the ring status of a module associated with a port
       "
    ::= { omnitronNotificationObjects 20 }


-- *****************************************************************************
-- Specific Notification Types
-- *****************************************************************************

icModcoldstrt NOTIFICATION-TYPE
    OBJECTS   { trapchassis, trapslot, trapcode, trapip, trapmoduledescription,
                trapmodetype, trapIpString }
    STATUS      current
    DESCRIPTION
       "Module Cold Start - a module has been plugged into a chassis"
    ::= { omnitronNotifications 1 }

icModsftreset NOTIFICATION-TYPE
    OBJECTS   { trapchassis, trapslot, trapcode, trapip, trapmoduledescription,
                trapmodetype, trapIpString }
    STATUS      current
    DESCRIPTION
       "Module Reset - the module received a reset command from the chassis
        data manager"
    ::= { omnitronNotifications 2 }

icModlinkdown NOTIFICATION-TYPE
    OBJECTS   { trapchassis, trapslot, trapcode, trapip, trapmoduledescription,
                trapmodetype, trapIpString }
    STATUS      current
    DESCRIPTION
       "Module Link Down - the module went from a link to a no link condition"
    ::= { omnitronNotifications 3 }

icModlinkup   NOTIFICATION-TYPE
    OBJECTS   { trapchassis, trapslot, trapcode, trapip, trapmoduledescription,
                trapmodetype, trapIpString }
    STATUS      current
    DESCRIPTION
       "Module Link Up - the module went from no link to a link condition"
    ::= { omnitronNotifications 4 }

icModdipsw    NOTIFICATION-TYPE
    OBJECTS   { trapchassis, trapslot, trapcode, trapip, trapmoduledescription,
                trapmodetype, trapIpString }
    STATUS      current
    DESCRIPTION
       "Module Dip Switch Change - the dip switches on the module were changed"
    ::= { omnitronNotifications 5 }

icModsoftcfg  NOTIFICATION-TYPE
    OBJECTS   { trapchassis, trapslot, trapcode, trapip, trapmoduledescription,
                trapmodetype, trapIpString }
    STATUS      current
    DESCRIPTION
       "Module Configuration Change - the module configuration was changed by
        external software and the hardware configuration may no longer
        reflect its true state"
    ::= { omnitronNotifications 6 }

icModovertemp NOTIFICATION-TYPE
    OBJECTS   { trapchassis, trapslot, trapcode, trapip, trapmoduledescription,
                trapmodetype, trapIpString }
    STATUS      current
    DESCRIPTION
       "Module Over Temperature - for modules with temperature sensing
        capabilities this trap indicates the temperature is over the acceptable
        limits for the module"
    ::= { omnitronNotifications 7 }

icModvoltrnge NOTIFICATION-TYPE
    OBJECTS   { trapchassis, trapslot, trapcode, trapip, trapmoduledescription,
                trapmodetype, trapIpString }
    STATUS      current
    DESCRIPTION
       "Module Voltage Range - for modules with voltage sensing capabilities
        this trap indicates the voltage is outside of the acceptable limits
        defined for the voltage being sensed"
    ::= { omnitronNotifications 8 }

icModpwrremv  NOTIFICATION-TYPE
    OBJECTS   { trapchassis, trapslot, trapcode, trapip, trapmoduledescription,
                trapmodetype, trapIpString }
    STATUS      current
    DESCRIPTION
       "Module Power Removed - A power supply's cord is no longer supplying
        power to it and the supply is no longer generating voltage. (For
        chassis with multiple supplies)"
    ::= { omnitronNotifications 9 }

icModpwrapply NOTIFICATION-TYPE
    OBJECTS   { trapchassis, trapslot, trapcode, trapip, trapmoduledescription,
                trapmodetype, trapIpString }
    STATUS      current
    DESCRIPTION
       "Module Power Applied - A power supply's cord was not supplying power
        and now it is.  The supply is generating voltage.  (for chassis with
        multiple supplies)"
    ::= { omnitronNotifications 10 }

icAuthfail  NOTIFICATION-TYPE
    OBJECTS   { trapchassis, trapslot, trapcode, trapip, trapmoduledescription,
                trapmodetype, eventSrcIp, eventSrcIpString, trapIpString }
    STATUS      current
    DESCRIPTION
       "Data Manager Authentication Failure - The name and password supplied to
        the SNMP agent did not match the ones configured into the data
        manager's user-settings."
    ::= { omnitronNotifications 11 }

icChasnew   NOTIFICATION-TYPE
    OBJECTS   { trapchassis, trapslot, trapcode, trapip, trapmoduledescription,
                trapmodetype, trapIpString }
    STATUS      current
    DESCRIPTION
       "Chassis New - a new chassis has been added to the system"
    ::= { omnitronNotifications 13 }

icChasgone NOTIFICATION-TYPE
    OBJECTS   { trapchassis, trapslot, trapcode, trapip, trapmoduledescription,
                trapmodetype, trapIpString }
    STATUS      current
    DESCRIPTION
       "Chassis Gone - a chassis has been removed from the system"
    ::= { omnitronNotifications 14 }

icModremove NOTIFICATION-TYPE
    OBJECTS   { trapchassis, trapslot, trapcode, trapip, trapmoduledescription,
                trapmodetype, trapIpString }
    STATUS      current
    DESCRIPTION
       "Module Remove - a module has been removed from chassis"
    ::= { omnitronNotifications 16 }

icPriAct NOTIFICATION-TYPE
    OBJECTS   { trapchassis, trapslot, trapcode, trapip, trapmoduledescription,
                trapmodetype, trapIpString }
    STATUS      current
    DESCRIPTION
       "Primary Link up"
    ::= { omnitronNotifications 17 }

icPriDis NOTIFICATION-TYPE
    OBJECTS   { trapchassis, trapslot, trapcode, trapip, trapmoduledescription,
                trapmodetype, trapIpString }
    STATUS      current
    DESCRIPTION
       "Primary Link down"
    ::= { omnitronNotifications 18 }

icSecAct NOTIFICATION-TYPE
    OBJECTS   { trapchassis, trapslot, trapcode, trapip, trapmoduledescription,
                trapmodetype, trapIpString }
    STATUS      current
    DESCRIPTION
       "Secondary Link up"
    ::= { omnitronNotifications 19 }

icSecDis NOTIFICATION-TYPE
    OBJECTS   { trapchassis, trapslot, trapcode, trapip, trapmoduledescription,
                trapmodetype, trapIpString }
    STATUS      current
    DESCRIPTION
       "Secondary Link down"
    ::= { omnitronNotifications 20 }

icTelStart NOTIFICATION-TYPE
    OBJECTS   { trapchassis, trapslot, trapcode, trapip, trapmoduledescription,
                trapmodetype, eventSrcIp, eventSrcIpString, trapIpString }
    STATUS      current
    DESCRIPTION
       "Telnet Session Started"
    ::= { omnitronNotifications 21 }

icTelStop NOTIFICATION-TYPE
    OBJECTS   { trapchassis, trapslot, trapcode, trapip, trapmoduledescription,
                trapmodetype, eventSrcIp, eventSrcIpString, trapIpString }
    STATUS      current
    DESCRIPTION
       "Telnet Session Stopped"
    ::= { omnitronNotifications 22 }

icFTPStart NOTIFICATION-TYPE
    OBJECTS   { trapchassis, trapslot, trapcode, trapip, trapmoduledescription,
                trapmodetype, eventSrcIp, eventSrcIpString, trapIpString }
    STATUS      current
    DESCRIPTION
       "FTP Session Started"
    ::= { omnitronNotifications 23 }

icFTPStop NOTIFICATION-TYPE
    OBJECTS   { trapchassis, trapslot, trapcode, trapip, trapmoduledescription,
                trapmodetype, eventSrcIp, eventSrcIpString, trapIpString }
    STATUS      current
    DESCRIPTION
       "FTP Session Stopped"
    ::= { omnitronNotifications 24 }

icStnAct NOTIFICATION-TYPE
    OBJECTS   { trapchassis, trapslot, trapcode, trapip, trapmoduledescription,
                trapmodetype, trapIpString }
    STATUS      current
    DESCRIPTION
       "Secondary Link Standby Up"
    ::= { omnitronNotifications 25 }

icStnDis NOTIFICATION-TYPE
    OBJECTS   { trapchassis, trapslot, trapcode, trapip, trapmoduledescription,
                trapmodetype, trapIpString }
    STATUS      current
    DESCRIPTION
       "Secondary Link Standby Down"
    ::= { omnitronNotifications 26 }

icPwdExceeded NOTIFICATION-TYPE
    OBJECTS   { trapchassis, trapslot, trapcode, trapip, trapmoduledescription,
                trapmodetype, eventSrcIp, eventSrcIpString, trapIpString }
    STATUS      current
    DESCRIPTION
       "Password Count Exceeded"
    ::= { omnitronNotifications 27 }

icROMchecksum NOTIFICATION-TYPE
    OBJECTS   { trapchassis, trapslot, trapcode, trapip, trapmoduledescription,
                trapmodetype, trapIpString }
    STATUS      current
    DESCRIPTION
       "Flash checksum error"
    ::= { omnitronNotifications 28 }

icROMFileType NOTIFICATION-TYPE
    OBJECTS   { trapchassis, trapslot, trapcode, trapip, trapmoduledescription,
                trapmodetype, trapIpString }
    STATUS      current
    DESCRIPTION
       "Flash file type incorrect"
    ::= { omnitronNotifications 29 }

icROMProgFail NOTIFICATION-TYPE
    OBJECTS   { trapchassis, trapslot, trapcode, trapip, trapmoduledescription,
                trapmodetype, trapIpString }
    STATUS      current
    DESCRIPTION
       "Flash program failure"
    ::= { omnitronNotifications 30 }

icROMFileChecksum NOTIFICATION-TYPE
    OBJECTS   { trapchassis, trapslot, trapcode, trapip, trapmoduledescription,
                trapmodetype, trapIpString }
    STATUS      current
    DESCRIPTION
       "Flash file transmission error"
    ::= { omnitronNotifications 31 }

icModuleFlashProgramComplete NOTIFICATION-TYPE
    OBJECTS   { trapchassis, trapslot, trapcode, trapip, trapmoduledescription,
                trapmodetype, trapIpString }
    STATUS      current
    DESCRIPTION
       "Module programming completed OK"
    ::= { omnitronNotifications 32 }

icDyingGasp NOTIFICATION-TYPE
    OBJECTS   { trapchassis, trapslot, trapcode, trapip, trapmoduledescription,
                trapmodetype, trapIpString }
    STATUS      current
    DESCRIPTION
       "Power failure detected, system shutting down"
    ::= { omnitronNotifications 33 }

icKeepAlive     NOTIFICATION-TYPE
    OBJECTS   { trapchassis, trapslot, trapcode, trapip, trapmoduledescription,
                trapmodetype, trapIpString }
    STATUS      current
    DESCRIPTION
       "Periodic trap to let management applications know device is still
        active"
    ::= { omnitronNotifications 34 }

icVlanCfgChange NOTIFICATION-TYPE
    OBJECTS   { trapchassis, trapslot, trapcode, trapip, trapmoduledescription,
                trapmodetype, trapIpString }
    STATUS      current
    DESCRIPTION
       "Module VLAN information has been changed"
    ::= { omnitronNotifications 35 }

icAISdetected   NOTIFICATION-TYPE
    OBJECTS   { trapchassis, trapslot, trapcode, trapip, trapmoduledescription,
                trapmodetype, trapIpString }
    STATUS      current
    DESCRIPTION
       "AIS Detected"
    ::= { omnitronNotifications 36 }

icPRBSdetected  NOTIFICATION-TYPE
    OBJECTS   { trapchassis, trapslot, trapcode, trapip, trapmoduledescription,
                trapmodetype, trapIpString }
    STATUS      current
    DESCRIPTION
       "PRBS Detected"
    ::= { omnitronNotifications 37 }

icChassisMastershipAcquired NOTIFICATION-TYPE
    OBJECTS   { trapchassis, trapslot, trapcode, trapip, trapmoduledescription,
                trapmodetype, trapIpString }
    STATUS      current
    DESCRIPTION
       "Management module has acquired mastership of the backplane"
    ::= { omnitronNotifications 39 }

icSecureModeChange NOTIFICATION-TYPE
    OBJECTS   { trapchassis, trapslot, trapcode, trapip, trapmoduledescription,
                trapmodetype, trapIpString }
    STATUS      current
    DESCRIPTION
       "Module has switched secure mode
           trapcode 0: secure -> normal (NMM master)
           trapcode 1: normal -> secure (NMM master)
           trapcode 2: secure -> normal (secure proxy)
           trapcode 3: normal -> secure (secure proxy)
           trapcode 4: secure -> normal (secure slave)
           trapcode 5: normal -> secure (secure slave)
       "
    ::= { omnitronNotifications 40 }

icChassisMastershipRelinquished NOTIFICATION-TYPE
    OBJECTS   { trapchassis, trapslot, trapcode, trapip, trapmoduledescription,
                trapmodetype, trapIpString }
    STATUS      current
    DESCRIPTION
       "Management module has relinquished mastership of the backplane"
    ::= { omnitronNotifications 41 }

icSFPDeviceInserted NOTIFICATION-TYPE
    OBJECTS   { trapchassis, trapslot, trapcode, trapip, trapmoduledescription,
                trapmodetype, trapIpString }
    STATUS      current
    DESCRIPTION
       "A SFP Device Inserted"
    ::= { omnitronNotifications 42 }

icSFPDeviceRemoved NOTIFICATION-TYPE
    OBJECTS   { trapchassis, trapslot, trapcode, trapip, trapmoduledescription,
                trapmodetype, trapIpString }
    STATUS      current
    DESCRIPTION
       "A SFP Device Removed"
    ::= { omnitronNotifications 43 }

icAHEventNotificationGenerated NOTIFICATION-TYPE
    OBJECTS   {trapchassis, trapslot, trapcode, trapip, trapmoduledescription,
               trapmodetype, eventNotificationType, eventNotificationErrors,
               eventNotificationErrorTotal, eventNotificationEventsTotal, trapIpString }
    STATUS      current
    DESCRIPTION
       "AH Link Event has been generated"
    ::= { omnitronNotifications 44 }

icAHEventNotificationReceived NOTIFICATION-TYPE
    OBJECTS   {trapchassis, trapslot, trapcode, trapip, trapmoduledescription,
               trapmodetype, eventNotificationType, eventNotificationErrors,
               eventNotificationErrorTotal, eventNotificationEventsTotal, trapIpString }
    STATUS      current
    DESCRIPTION
       "AH Link Event has been received"
    ::= { omnitronNotifications 45 }

icContactStatusChange NOTIFICATION-TYPE
    OBJECTS   { trapchassis, trapslot, trapcode, trapip, trapmoduledescription,
                trapmodetype, contactClosureStatus, trapIpString }
    STATUS      current
    DESCRIPTION
       "Contact closure status change detected"
    ::= { omnitronNotifications 46 }

icAHLinkFaultReceived NOTIFICATION-TYPE
    OBJECTS   { trapchassis, trapslot, trapcode, trapip, trapmoduledescription,
                trapmodetype, trapIpString }
    STATUS      current
    DESCRIPTION
       "A link fault has been received over AH connection"
    ::= { omnitronNotifications 47 }

icAHCriticalEventGenerated NOTIFICATION-TYPE
    OBJECTS   { trapchassis, trapslot, trapcode, trapip, trapmoduledescription,
                trapmodetype, trapIpString }
    STATUS      current
    DESCRIPTION
       "A critical event has been generated"
    ::= { omnitronNotifications 48 }

icAHCriticalEventReceived NOTIFICATION-TYPE
    OBJECTS   { trapchassis, trapslot, trapcode, trapip, trapmoduledescription,
                trapmodetype, trapIpString }
    STATUS      current
    DESCRIPTION
       "A critical event has been received"
    ::= { omnitronNotifications 49 }

icAHRemoteDyingGasp NOTIFICATION-TYPE
    OBJECTS   { trapchassis, trapslot, trapcode, trapip, trapmoduledescription,
                trapmodetype, trapIpString }
    STATUS      current
    DESCRIPTION
       "Power failure detected from remote partner, system shutting down"
    ::= { omnitronNotifications 50 }

icResource NOTIFICATION-TYPE
    OBJECTS   { trapchassis, trapslot, trapcode, trapip, trapmoduledescription,
                trapmodetype, trapIpString }
    STATUS      current
    DESCRIPTION
       "Generated when an internal resource is fully allocated.  Specific
        resource is defined by the Trap code."
    ::= { omnitronNotifications 51 }

icLoopbackReplyReceived NOTIFICATION-TYPE
    OBJECTS   { trapchassis, trapslot, trapcode, trapip, trapmoduledescription,
                trapmodetype, trapIpString }
    STATUS      current
    DESCRIPTION
       "Generated when the  T1/E1, T3/E3 remote module responds to a loopback
        request"
    ::= { omnitronNotifications 52 }

icLoopbackReplyLost NOTIFICATION-TYPE
    OBJECTS   { trapchassis, trapslot, trapcode, trapip, trapmoduledescription,
                trapmodetype, trapIpString }
    STATUS      current
    DESCRIPTION
       "Generated when the T1/E1, T3/E3 remote module stops sending a loopback
        reply"
    ::= { omnitronNotifications 53 }

icCfmFaultAlarm NOTIFICATION-TYPE
    OBJECTS   { trapchassis, trapslot, trapcode, trapip, trapmoduledescription,
                trapmodetype, trapAgMdIndex, trapAgMaIndex, trapAgMepId,
                trapAgErrorCode, trapIpString }
    STATUS      current
    DESCRIPTION
       "Generated when an 802.1ag MEP has a persistent defect condition,
        trapcode has the port number"
    ::= { omnitronNotifications 54 }

icCfmLoopBackComplete NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag loopback command has completed."
    ::= { omnitronNotifications 55 }

icCfmLinkTraceComplete NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag Link Trace command has completed."
    ::= { omnitronNotifications 56 }

icCfmMepUp NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag MEP is discovered, service is restored, or
        status of report port changes."
    ::= { omnitronNotifications 57 }

icCfmMepDown NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag MEP timeout occurs."
    ::= { omnitronNotifications 58 }

icCfmMepCrossConnect NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag service ID does not match the VLAN or is at
        a lower MD level."
    ::= { omnitronNotifications 59 }

icCfmLoop NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag MEP receives its own CCM or MEPID."
    ::= { omnitronNotifications 60 }

icCfmConfigError NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag MEP receives an incorrect CCM."
    ::= { omnitronNotifications 61 }

icCfmAllMepsUp NOTIFICATION-TYPE
    OBJECTS   { trapchassis, trapslot, trapcode, trapip, trapmoduledescription,
                trapmodetype, trapAgMdIndex, trapAgMaIndex, trapAgMepId, trapIpString }
    STATUS      current
    DESCRIPTION
       "Generated when all 802.1ag expected MEPs are up in time."
    ::= { omnitronNotifications 62 }

icCfmMepUnknown NOTIFICATION-TYPE
    OBJECTS   { trapchassis, trapslot, trapcode, trapip, trapmoduledescription,
                trapmodetype, trapAgMdIndex, trapAgMaIndex, trapAgMepId, trapIpString }
    STATUS      current
    DESCRIPTION
       "Generated when an 802.1ag CCM is received from an unexpected MEP."
    ::= { omnitronNotifications 64 }

icSfpTxLow NOTIFICATION-TYPE
    OBJECTS   { trapchassis, trapslot, trapcode, trapip, trapmoduledescription,
                trapmodetype, trapIpString }
    STATUS      current
    DESCRIPTION
       "Generated when the measured Tx power is less than the low threshold."
    ::= { omnitronNotifications 73 }

icSfpTxHigh NOTIFICATION-TYPE
    OBJECTS   { trapchassis, trapslot, trapcode, trapip, trapmoduledescription,
                trapmodetype, trapIpString }
    STATUS      current
    DESCRIPTION
       "Generated when the measured Tx power is greater than the high
        threshold."
    ::= { omnitronNotifications 74 }

icSfpBiasLow NOTIFICATION-TYPE
    OBJECTS   { trapchassis, trapslot, trapcode, trapip, trapmoduledescription,
                trapmodetype, trapIpString }
    STATUS      current
    DESCRIPTION
       "Generated when the measured bias voltage is less than the low
        threshold."
    ::= { omnitronNotifications 75 }

icSfpBiasHigh NOTIFICATION-TYPE
    OBJECTS   { trapchassis, trapslot, trapcode, trapip, trapmoduledescription,
                trapmodetype, trapIpString }
    STATUS      current
    DESCRIPTION
       "Generated when the measured bias voltage is greater than the high
        threshold."
    ::= { omnitronNotifications 76 }

icSfpVcc3Low NOTIFICATION-TYPE
    OBJECTS   { trapchassis, trapslot, trapcode, trapip, trapmoduledescription,
                trapmodetype, trapIpString }
    STATUS      current
    DESCRIPTION
       "Generated when the measured voltage is less than the low threshold."
    ::= { omnitronNotifications 77 }

icSfpVcc3High NOTIFICATION-TYPE
    OBJECTS   { trapchassis, trapslot, trapcode, trapip, trapmoduledescription,
                trapmodetype, trapIpString }
    STATUS      current
    DESCRIPTION
       "Generated when the measured voltage is greater than the high threshold."
    ::= { omnitronNotifications 78 }

icSfpTempLow NOTIFICATION-TYPE
    OBJECTS   { trapchassis, trapslot, trapcode, trapip, trapmoduledescription,
                trapmodetype, trapIpString }
    STATUS      current
    DESCRIPTION
       "Generated when the measured temperature is less than the low threshold."
    ::= { omnitronNotifications 79 }

icSfpTempHigh NOTIFICATION-TYPE
    OBJECTS   { trapchassis, trapslot, trapcode, trapip, trapmoduledescription,
                trapmodetype, trapIpString }
    STATUS      current
    DESCRIPTION
       "Generated when the measured temperature is greater than the high
        threshold."
    ::= { omnitronNotifications 80 }

icSfpAux2Low NOTIFICATION-TYPE
    OBJECTS   { trapchassis, trapslot, trapcode, trapip, trapmoduledescription,
                trapmodetype, trapIpString }
    STATUS      current
    DESCRIPTION
       "Generated when the measured Aux 2 value is less than the low threshold."
    ::= { omnitronNotifications 81 }

icSfpAux2High NOTIFICATION-TYPE
    OBJECTS   { trapchassis, trapslot, trapcode, trapip, trapmoduledescription,
                trapmodetype, trapIpString }
    STATUS      current
    DESCRIPTION
       "Generated when the measured Aux 2 value is greater than the high
        threshold."
    ::= { omnitronNotifications 82 }

icSfpAux1Low NOTIFICATION-TYPE
    OBJECTS   { trapchassis, trapslot, trapcode, trapip, trapmoduledescription,
                trapmodetype, trapIpString }
    STATUS      current
    DESCRIPTION
       "Generated when the measured Aux 1 value is less than the low threshold."
    ::= { omnitronNotifications 83 }

icSfpAux1High NOTIFICATION-TYPE
    OBJECTS   { trapchassis, trapslot, trapcode, trapip, trapmoduledescription,
                trapmodetype, trapIpString }
    STATUS      current
    DESCRIPTION
       "Generated when the measured Aux 1 value is greater than the high
        threshold."
    ::= { omnitronNotifications 84 }

icSfpRxLow NOTIFICATION-TYPE
    OBJECTS   { trapchassis, trapslot, trapcode, trapip, trapmoduledescription,
                trapmodetype, trapIpString }
    STATUS      current
    DESCRIPTION
       "Generated when the measured Rx power is less than the low threshold."
    ::= { omnitronNotifications 85 }

icSfpRxHigh NOTIFICATION-TYPE
    OBJECTS   { trapchassis, trapslot, trapcode, trapip, trapmoduledescription,
                trapmodetype, trapIpString }
    STATUS      current
    DESCRIPTION
       "Generated when the measured Rx power is greater than the high
        threshold."
    ::= { omnitronNotifications 86 }

icSfpVcc2Low NOTIFICATION-TYPE
    OBJECTS   { trapchassis, trapslot, trapcode, trapip, trapmoduledescription,
                trapmodetype, trapIpString }
    STATUS      current
    DESCRIPTION
       "Generated when the measured voltage is less than the low threshold."
    ::= { omnitronNotifications 87 }

icSfpVcc2High NOTIFICATION-TYPE
    OBJECTS   { trapchassis, trapslot, trapcode, trapip, trapmoduledescription,
                trapmodetype, trapIpString }
    STATUS      current
    DESCRIPTION
       "Generated when the measured voltage is greater than the high threshold."
    ::= { omnitronNotifications 88 }

icSfpVcc5Low NOTIFICATION-TYPE
    OBJECTS   { trapchassis, trapslot, trapcode, trapip, trapmoduledescription,
                trapmodetype, trapIpString }
    STATUS      current
    DESCRIPTION
       "Generated when the measured voltage is less than the low threshold."
    ::= { omnitronNotifications 89 }

icSfpVcc5High NOTIFICATION-TYPE
    OBJECTS   { trapchassis, trapslot, trapcode, trapip, trapmoduledescription,
                trapmodetype, trapIpString }
    STATUS      current
    DESCRIPTION
       "Generated when the measured voltage is greater than the high threshold."
    ::= { omnitronNotifications 90 }

icLineChange NOTIFICATION-TYPE
    OBJECTS   { trapchassis, trapslot, trapcode, trapip, trapmoduledescription,
                trapmodetype, dsx1LineStatus, dsx1LineStatusLastChange, trapIpString }
    STATUS      current
    DESCRIPTION
       "OST equivalent of the DS1 MIB dsx1LineStatusChange."
    ::= { omnitronNotifications 91 }

icConfigChange NOTIFICATION-TYPE
    OBJECTS   { trapchassis, trapslot, trapcode, trapip, trapmoduledescription,
                trapmodetype, trapIpString }
    STATUS      current
    DESCRIPTION
       "Configuration change has been committed to flash."
    ::= { omnitronNotifications 92 }

icLoopbackActivation NOTIFICATION-TYPE
    OBJECTS   { trapchassis, trapslot, trapcode, trapip, trapmoduledescription,
                trapmodetype, trapIpString }
    STATUS      current
    DESCRIPTION
       "Loopback Activation - loopback mode entered on remote device."
    ::= { omnitronNotifications 93 }

icLoopbackDeactivation NOTIFICATION-TYPE
    OBJECTS   { trapchassis, trapslot, trapcode, trapip, trapmoduledescription,
                trapmodetype, trapIpString }
    STATUS      current
    DESCRIPTION
       "Loopback Deactivation - normal mode entered on remote device."
    ::= { omnitronNotifications 94 }

icTimingError NOTIFICATION-TYPE
    OBJECTS   { trapchassis, trapslot, trapcode, trapip, trapmoduledescription,
                trapmodetype, trapIpString }
    STATUS      current
    DESCRIPTION
       "Timing Error or Clock Slip."
    ::= { omnitronNotifications 95 }

icFramingOverrun NOTIFICATION-TYPE
    OBJECTS   { trapchassis, trapslot, trapcode, trapip, trapmoduledescription,
                trapmodetype, trapIpString }
    STATUS      current
    DESCRIPTION
       "Data Framing Overrun."
    ::= { omnitronNotifications 96 }

icDataUnderrun NOTIFICATION-TYPE
    OBJECTS   { trapchassis, trapslot, trapcode, trapip, trapmoduledescription,
                trapmodetype, trapIpString }
    STATUS      current
    DESCRIPTION
       "Data Framing Under run."
    ::= { omnitronNotifications 97 }

icRemoteFound NOTIFICATION-TYPE
    OBJECTS   { trapchassis, trapslot, trapcode, trapip, trapmoduledescription,
                trapmodetype, trapIpString }
    STATUS      current
    DESCRIPTION
       "Remote Unit Found."
    ::= { omnitronNotifications 98 }

icHardwareFault     NOTIFICATION-TYPE
    OBJECTS   { trapchassis, trapslot, trapcode, trapip, trapmoduledescription,
                trapmodetype, trapIpString }
    STATUS      current
    DESCRIPTION
       "Module Hardware Failure"
    ::= { omnitronNotifications 99 }

icRemoteLost NOTIFICATION-TYPE
    OBJECTS   { trapchassis, trapslot, trapcode, trapip, trapmoduledescription,
                trapmodetype, trapIpString }
    STATUS      current
    DESCRIPTION
       "Remote Unit Lost."
    ::= { omnitronNotifications 100 }

icRemoteError NOTIFICATION-TYPE
    OBJECTS   { trapchassis, trapslot, trapcode, trapip, trapmoduledescription,
                trapmodetype, trapIpString }
    STATUS      current
    DESCRIPTION
       "Remote Unit Error Detected."
    ::= { omnitronNotifications 101 }

icRemoteGood NOTIFICATION-TYPE
    OBJECTS   { trapchassis, trapslot, trapcode, trapip, trapmoduledescription,
                trapmodetype, trapIpString }
    STATUS      current
    DESCRIPTION
       "Remote Unit Good Detected."
    ::= { omnitronNotifications 102 }

icExternalClockLost NOTIFICATION-TYPE
    OBJECTS   { trapchassis, trapslot, trapcode, trapip, trapmoduledescription,
                trapmodetype, trapIpString }
    STATUS      current
    DESCRIPTION
       "The external clock source has been lost."
    ::= { omnitronNotifications 103 }

icSerStart NOTIFICATION-TYPE
    OBJECTS   { trapchassis, trapslot, trapcode, trapip, trapmoduledescription,
                trapmodetype, trapIpString }
    STATUS      current
    DESCRIPTION
       "Serial Session Started."
    ::= { omnitronNotifications 104 }

icSerStop NOTIFICATION-TYPE
    OBJECTS   { trapchassis, trapslot, trapcode, trapip, trapmoduledescription,
                trapmodetype, trapIpString }
    STATUS      current
    DESCRIPTION
       "Serial Session Stopped."
    ::= { omnitronNotifications 105 }

icSFPOverPower NOTIFICATION-TYPE
    OBJECTS   { trapchassis, trapslot, trapcode, trapip, trapmoduledescription,
                trapmodetype, trapIpString }
    STATUS      current
    DESCRIPTION
       "SFP is consuming too much power."
    ::= { omnitronNotifications 106 }

icRemoteTestActivation NOTIFICATION-TYPE
    OBJECTS   { trapchassis, trapslot, trapcode, trapip, trapmoduledescription,
                trapmodetype, trapIpString }
    STATUS      current
    DESCRIPTION
       "Remote Test Activation - test mode entered on remote device."
    ::= { omnitronNotifications 107 }

icRemoteTestDeactivation NOTIFICATION-TYPE
    OBJECTS   { trapchassis, trapslot, trapcode, trapip, trapmoduledescription,
                trapmodetype, trapIpString }
    STATUS      current
    DESCRIPTION
       "Remote Test Deactivation - test mode exited on remote device."
    ::= { omnitronNotifications 108 }

icLocalTestActivation NOTIFICATION-TYPE
    OBJECTS   { trapchassis, trapslot, trapcode, trapip, trapmoduledescription,
                trapmodetype, trapIpString }
    STATUS      current
    DESCRIPTION
       "Local Test Activation - test mode entered on local device."
    ::= { omnitronNotifications 109 }

icLocalTestDeactivation NOTIFICATION-TYPE
    OBJECTS   { trapchassis, trapslot, trapcode, trapip, trapmoduledescription,
                trapmodetype, trapIpString }
    STATUS      current
    DESCRIPTION
       "Local Test Deactivation - test mode exited on local device."
    ::= { omnitronNotifications 110 }

icAuthSshFail NOTIFICATION-TYPE
    OBJECTS   { trapchassis, trapslot, trapcode, trapip, trapmoduledescription,
                trapmodetype, eventSrcIp, eventSrcIpString, trapIpString }
    STATUS      current
    DESCRIPTION
       "SSH Authentication Failure - Authentication type/password did not match
        configured setting."
    ::= { omnitronNotifications 111 }

icSshStart NOTIFICATION-TYPE
    OBJECTS   { trapchassis, trapslot, trapcode, trapip, trapmoduledescription,
                trapmodetype, eventSrcIp, eventSrcIpString, trapIpString }
    STATUS      current
    DESCRIPTION
       "SSH Session Started - The management module has detected that a SSH
        session has started."
    ::= { omnitronNotifications 112 }

icSshStop NOTIFICATION-TYPE
    OBJECTS   { trapchassis, trapslot, trapcode, trapip, trapmoduledescription,
                trapmodetype, eventSrcIp, eventSrcIpString, trapIpString }
    STATUS      current
    DESCRIPTION
       "SSH Session Stopped - The management module has detected that a SSH
        session has stopped."
    ::= { omnitronNotifications 113 }

icFileCorrupt NOTIFICATION-TYPE
    OBJECTS   { trapchassis, trapslot, trapcode, trapip, trapmoduledescription,
                trapmodetype, trapIpString }
    STATUS      current
    DESCRIPTION
       "Configuration File Corrupted - The management module has detected a
        corrupted configuration file."
    ::= { omnitronNotifications 114 }

icProtectionSwitch NOTIFICATION-TYPE
    OBJECTS   { trapchassis, trapslot, trapcode, trapip, trapmoduledescription,
                trapmodetype, trapAgMdIndex, trapAgMaIndex, trapAgMepId, 
                trapIpString }
    STATUS      current
    DESCRIPTION
       "Protection Switch - trap generated when a protection switch occurs."
    ::= { omnitronNotifications 115 }

icProtectionMismatch NOTIFICATION-TYPE
    OBJECTS   { trapchassis, trapslot, trapcode, trapip, trapmoduledescription,
                trapmodetype, trapAgMdIndex, trapAgMaIndex, trapAgMepId, trapIpString }
    STATUS      current
    DESCRIPTION
       "Protection Configuration Mismatch - trap generated when a protection
        configuration mismatch occurs."
    ::= { omnitronNotifications 116 }

icFanNoRpm NOTIFICATION-TYPE
    OBJECTS   { trapchassis, trapslot, trapcode, trapip, trapmoduledescription,
                trapmodetype, trapIpString }
    STATUS      current
    DESCRIPTION
       "Fan Rotation Not Detected - Detected no or low RPMs generated from the
        fan."
    ::= { omnitronNotifications 117 }

icFanHighRpm NOTIFICATION-TYPE
    OBJECTS   { trapchassis, trapslot, trapcode, trapip, trapmoduledescription,
                trapmodetype, trapIpString }
    STATUS      current
    DESCRIPTION
       "Fan Rotation High Threshold - Detected fan rotation speed is high."
    ::= { omnitronNotifications 118 }

icFpgaFailure NOTIFICATION-TYPE
    OBJECTS   { trapchassis, trapslot, trapcode, trapip, trapmoduledescription,
                trapmodetype, trapIpString }
    STATUS      current
    DESCRIPTION
       "FPGA Failure - FPGA initialization failure."
    ::= { omnitronNotifications 119 }

icFanNormalRpm NOTIFICATION-TYPE
    OBJECTS   { trapchassis, trapslot, trapcode, trapip, trapmoduledescription,
                trapmodetype, trapIpString }
    STATUS      current
    DESCRIPTION
       "Fan Rotation Normal - Detected normal fan rotation speed"
    ::= { omnitronNotifications 120 }

ic1588SyncGained NOTIFICATION-TYPE
    OBJECTS   { trapchassis, trapslot, trapcode, trapip, trapmoduledescription,
                trapmodetype, trapIpString }
    STATUS      current
    DESCRIPTION
       "1588 Synchronization - Synchronization with 1588 master is gained"
    ::= { omnitronNotifications 121 }

ic1588SyncLost NOTIFICATION-TYPE
    OBJECTS   { trapchassis, trapslot, trapcode, trapip, trapmoduledescription,
                trapmodetype, trapIpString }
    STATUS      current
    DESCRIPTION
       "1588 Synchronization - Synchronization with 1588 master is lost"
    ::= { omnitronNotifications 122 }

ic1588PrimaryActive NOTIFICATION-TYPE
    OBJECTS   { trapchassis, trapslot, trapcode, trapip, trapmoduledescription,
                trapmodetype, trapIpString }
    STATUS      current
    DESCRIPTION
       "1588 Master - Primary Master is Active"
    ::= { omnitronNotifications 123 }

ic1588PrimaryInactive NOTIFICATION-TYPE
    OBJECTS   { trapchassis, trapslot, trapcode, trapip, trapmoduledescription,
                trapmodetype, trapIpString }
    STATUS      current
    DESCRIPTION
       "1588 Master - Primary Master Inactive"
    ::= { omnitronNotifications 124 }

ic1588SecondaryActive NOTIFICATION-TYPE
    OBJECTS   { trapchassis, trapslot, trapcode, trapip, trapmoduledescription,
                trapmodetype, trapIpString }
    STATUS      current
    DESCRIPTION
       "1588 Master - Secondary Master Active"
    ::= { omnitronNotifications 125 }

ic1588SecondaryInactive NOTIFICATION-TYPE
    OBJECTS   { trapchassis, trapslot, trapcode, trapip, trapmoduledescription,
                trapmodetype, trapIpString }
    STATUS      current
    DESCRIPTION
       "1588 Master - Secondary Master Inactive"
    ::= { omnitronNotifications 126 }

icSyncEthernetSourceGained NOTIFICATION-TYPE
    OBJECTS   { trapchassis, trapslot, trapcode, trapip, trapmoduledescription,
                trapmodetype, trapIpString }
    STATUS      current
    DESCRIPTION
       "Synchronous Ethernet - Synchronous Ethernet Clock Source Gained"
    ::= { omnitronNotifications 127 }

icSyncEthernetSourceLost NOTIFICATION-TYPE
    OBJECTS   { trapchassis, trapslot, trapcode, trapip, trapmoduledescription,
                trapmodetype, trapIpString }
    STATUS      current
    DESCRIPTION
       "Synchronous Ethernet - Synchronous Ethernet Clock Source Lost"
    ::= { omnitronNotifications 128 }

icSyncEthernetHoldoverLost NOTIFICATION-TYPE
    OBJECTS   { trapchassis, trapslot, trapcode, trapip, trapmoduledescription,
                trapmodetype, trapIpString }
    STATUS      current
    DESCRIPTION
       "Synchronous Ethernet - Synchronous Ethernet Clock Holdover Lost"
    ::= { omnitronNotifications 129 }

icAisAlarm NOTIFICATION-TYPE
    OBJECTS   { trapchassis, trapslot, trapcode, trapip, trapmoduledescription,
                trapmodetype, trapAgMdIndex, trapAgMaIndex, trapAgMepId,
                mefSoamAisStatsInStatus, mefSoamAisStatsOutStatus, trapIpString }
    STATUS      current
    DESCRIPTION
       "AIS State Change - OAM AIS reception or transmission state has changed"
    ::= { omnitronNotifications 130 }

icLckAlarm NOTIFICATION-TYPE
    OBJECTS   { trapchassis, trapslot, trapcode, trapip, trapmoduledescription,
                trapmodetype, trapAgMdIndex, trapAgMaIndex, trapAgMepId,
                mefSoamLckStatsInStatus, mefSoamLckStatsOutStatus, trapIpString }
    STATUS      current
    DESCRIPTION
       "LCK State Change - OAM ETH-LCK  reception or transmission state has
        changed"
    ::= { omnitronNotifications 131 }

icThresholdCrossing NOTIFICATION-TYPE
    OBJECTS   { trapchassis, trapslot, trapcode, trapip, trapmoduledescription,
                trapmodetype, trapAgMdIndex, trapAgMaIndex, trapAgMepId,
                eventThresholdIdentification, trapIpString }
    STATUS      current
    DESCRIPTION
       "Threshold Crossing - Performance Criteria Measurement not met. This
        trap should be generated at most once every 5 minutes.
       "
    ::= { omnitronNotifications 132 }

icThresholdCrossingClear NOTIFICATION-TYPE
    OBJECTS   { trapchassis, trapslot, trapcode, trapip, trapmoduledescription,
                trapmodetype, trapAgMdIndex, trapAgMaIndex, trapAgMepId,
                eventThresholdIdentification, trapIpString }
    STATUS      current
    DESCRIPTION
       "Threshold Crossing - Performance Criteria Measurement met"
    ::= { omnitronNotifications 133 }

icTdmClockStatusChange NOTIFICATION-TYPE
    OBJECTS   { trapchassis, trapslot, trapcode, trapip, trapmoduledescription,
                trapmodetype, eventPortClockState, trapIpString }
    STATUS      current
    DESCRIPTION
       "TDM Clock Status Change - Status of TDM recovery clock changed"
    ::= { omnitronNotifications 134 }

icTdmEthernetFrameCount NOTIFICATION-TYPE
    OBJECTS   { trapchassis, trapslot, trapcode, trapip, trapmoduledescription,
                trapmodetype, trapIpString }
    STATUS      current
    DESCRIPTION
       "TDM Ethernet Frame Count - Incorrect number of Ethernet frames"
    ::= { omnitronNotifications 135 }

icSfpReceiveCdrLossLock NOTIFICATION-TYPE
    OBJECTS   { trapchassis, trapslot, trapcode, trapip, trapmoduledescription,
                trapmodetype, trapIpString }
    STATUS      current
    DESCRIPTION
       "SFP/XFP Receive CDR Loss of Lock"
    ::= { omnitronNotifications 136 }

icSfpTransmitCdrLossLock NOTIFICATION-TYPE
    OBJECTS   { trapchassis, trapslot, trapcode, trapip, trapmoduledescription,
                trapmodetype, trapIpString }
    STATUS      current
    DESCRIPTION
       "SFP/XFP transmitted loses CDR lock"
    ::= { omnitronNotifications 137 }

icDpoeStageWarningAlarm NOTIFICATION-TYPE
    OBJECTS   { trapchassis, trapslot, trapcode, trapip, trapmoduledescription,
                trapmodetype, eventDpoeStageNumber, eventSetClear, trapIpString }
    STATUS      current
    DESCRIPTION
       "DPoE Stage warning alarm. Alarm is sent when the alarm state changes to
        either set or clear. Only one stage warning alarm can be set at one
        time.
       "
    ::= { omnitronNotifications 138 }

icDpoeStageFailAlarm NOTIFICATION-TYPE
    OBJECTS   { trapchassis, trapslot, trapcode, trapip, trapmoduledescription,
                trapmodetype, eventDpoeStageNumber, eventSetClear, trapIpString }
    STATUS      current
    DESCRIPTION
       "DPoE Stage failure alarm. Alarm is sent when the alarm state changes to
        either set or clear.  Only one stage fail alarm can be set at one time.
       "
    ::= { omnitronNotifications 139 }

icSfpReceiveCdrGainedLock NOTIFICATION-TYPE
    OBJECTS   { trapchassis, trapslot, trapcode, trapip, trapmoduledescription,
                trapmodetype, trapIpString }
    STATUS      current
    DESCRIPTION
       "SFP/XFP receiver gained CDR lock"
    ::= { omnitronNotifications 140 }

icSfpTransmitCdrGainedLock NOTIFICATION-TYPE
    OBJECTS   { trapchassis, trapslot, trapcode, trapip, trapmoduledescription,
                trapmodetype, trapIpString }
    STATUS      current
    DESCRIPTION
       "SFP/XFP transmitted gained CDR lock"
    ::= { omnitronNotifications 141 }

icModNormalTemp NOTIFICATION-TYPE
    OBJECTS   { trapchassis, trapslot, trapcode, trapip, trapmoduledescription,
                trapmodetype, trapIpString }
    STATUS      current
    DESCRIPTION
       "Module normal temperature"
    ::= { omnitronNotifications 142 }

icModNormalVoltage NOTIFICATION-TYPE
    OBJECTS   { trapchassis, trapslot, trapcode, trapip, trapmoduledescription,
                trapmodetype, trapIpString }
    STATUS      current
    DESCRIPTION
       "Module normal voltage range"
    ::= { omnitronNotifications 143 }

icPortNormalData NOTIFICATION-TYPE
    OBJECTS   { trapchassis, trapslot, trapcode, trapip, trapmoduledescription,
                trapmodetype, trapIpString }
    STATUS      current
    DESCRIPTION
       "Module data detected"
    ::= { omnitronNotifications 144 }

icLinkOamRemoteLinkNormal NOTIFICATION-TYPE
    OBJECTS   { trapchassis, trapslot, trapcode, trapip, trapmoduledescription,
                trapmodetype, trapIpString }
    STATUS      current
    DESCRIPTION
       "802.3ah remote link normal"
    ::= { omnitronNotifications 145 }

icLinkOamLocalLinkNormal NOTIFICATION-TYPE
    OBJECTS   { trapchassis, trapslot, trapcode, trapip, trapmoduledescription,
                trapmodetype, trapIpString }
    STATUS      current
    DESCRIPTION
       "802.3ah local link normal"
    ::= { omnitronNotifications 146 }

icSfpNormal NOTIFICATION-TYPE
    OBJECTS   { trapchassis, trapslot, trapcode, trapip, trapmoduledescription,
                trapmodetype, trapIpString }
    STATUS      current
    DESCRIPTION
       "XFP/SFP normal"
    ::= { omnitronNotifications 147 }

icPoEPdStatus NOTIFICATION-TYPE
    OBJECTS   { trapchassis, trapslot, trapcode, trapip, trapmoduledescription,
                trapmodetype, eventPdStatus, trapIpString }
    STATUS      current
    DESCRIPTION
       "PoE PD Status Change"
    ::= { omnitronNotifications 148 }

icProbePriorityChange NOTIFICATION-TYPE
    OBJECTS   { trapchassis, trapslot, trapcode, trapip, trapmoduledescription,
                trapmodetype, trapAgMdIndex, trapAgMaIndex, trapAgMepId,
                eventProbePriorityNew, eventProbePriorityOld, trapIpString
              }
    STATUS      current
    DESCRIPTION
       "Generated when a Y.1731 probe priority changes.

        Currently this is only valid for DMR reception.

        'trapcode' indicates the probe instance number.
       "
    ::= { omnitronNotifications 149 }


icAuthFtpFail NOTIFICATION-TYPE
    OBJECTS   { trapchassis, trapslot, trapcode, trapip, trapmoduledescription,
                trapmodetype, eventSrcIp, eventSrcIpString, trapIpString }
    STATUS      current
    DESCRIPTION
       "FTP Authentication Failure - Authentication type/password did not match
        configured setting."
    ::= { omnitronNotifications 150 }

icAclDeny NOTIFICATION-TYPE
    OBJECTS   { trapchassis, trapslot, trapcode, trapip, trapmoduledescription,
                trapmodetype, eventSrcIp, eventAclNumber, eventSrcIpString, trapIpString }
    STATUS      current
    DESCRIPTION
       "ACL denial. Access is not allowed by configured ACL's. This trap
        only to be generated at most once a minute.
       "
    ::= { omnitronNotifications 151 }

icLinkOamDiscoveryComplete NOTIFICATION-TYPE
    OBJECTS   { trapchassis, trapslot, trapcode, trapip, trapmoduledescription,
                trapmodetype, trapIpString }
    STATUS      current
    DESCRIPTION
       "The module has detected Link OAM discovery completion on a port and is
        generated when discovery completes.
       "
    ::= { omnitronNotifications 152 }

icLinkOamDiscoveryLost NOTIFICATION-TYPE
    OBJECTS   { trapchassis, trapslot, trapcode, trapip, trapmoduledescription,
                trapmodetype, trapIpString }
    STATUS      current
    DESCRIPTION
       "The module has detected Link OAM discovery has been lost on a port and
        is generated when a Link OAM discovery had previously been completed on
        a port, but is now lost.
       "
    ::= { omnitronNotifications 153 }

icServiceActivationTestInitiated NOTIFICATION-TYPE
    OBJECTS   { trapchassis, trapslot, trapcode, trapip, trapmoduledescription,
                trapmodetype, trapIpString }
    STATUS      current
    DESCRIPTION
       "The module has initiated a Service Activation Test: either a 2544 or
        ITU-T Y.1564 test.
       "
    ::= { omnitronNotifications 154 }

icServiceActivationTestCompleted NOTIFICATION-TYPE
    OBJECTS   { trapchassis, trapslot, trapcode, trapip, trapmoduledescription,
                trapmodetype, trapIpString }
    STATUS      current
    DESCRIPTION
       "The module has completed a Service Activation Test: either a 2544 or
        ITU-T Y.1564 test.
       "
    ::= { omnitronNotifications 155 }

icUtilizationThresholdViolation NOTIFICATION-TYPE
    OBJECTS   { trapchassis, trapslot, trapcode, trapip, trapmoduledescription,
                trapmodetype, trapIpString }
    STATUS      current
    DESCRIPTION
       "The module has detected a utilization threshold violation on a port or
        a bandwidth profile. trapcode of 1-99 indicate a port threshold
        violation. trapcode of 101-164 indicate the bandwidth profile number

        This trap can only be generated if the threshold has not been
        violated for 5 seconds.
       "
    ::= { omnitronNotifications 156 }

icUtilizationThresholdNormal NOTIFICATION-TYPE
    OBJECTS   { trapchassis, trapslot, trapcode, trapip, trapmoduledescription,
                trapmodetype, trapIpString }
    STATUS      current
    DESCRIPTION
       "The module has detected a utilization threshold violation has cleared
        on a port or a bandwidth profile number.

        This trap can only be generated once a threshold violation has been
        cleared for 5 seconds.
       "
    ::= { omnitronNotifications 157 }

 icLoopPreventionBlock NOTIFICATION-TYPE
    OBJECTS   { trapchassis, trapslot, trapcode, trapip, trapmoduledescription,
                trapmodetype, trapIpString }
    STATUS      current
    DESCRIPTION
       "The module has detected loop condition and a loop prevention block on
        the port has occurred.
       "
    ::= { omnitronNotifications 158 }

 icLoopPreventionClear NOTIFICATION-TYPE
    OBJECTS   { trapchassis, trapslot, trapcode, trapip, trapmoduledescription,
                trapmodetype, trapIpString }
    STATUS      current
    DESCRIPTION
       "The module has detected that a loop condition has been cleared and
        the loop prevention block on the port has been removed.
       "
    ::= { omnitronNotifications 159 }

 icAuthTelnetFail NOTIFICATION-TYPE
    OBJECTS   { trapchassis, trapslot, trapcode, trapip, trapmoduledescription,
                trapmodetype, trapIpString }
    STATUS      current
    DESCRIPTION
       "Telnet Authentication Failure - Telnet user name and/or password did not
        match.
       "
    ::= { omnitronNotifications 160 }

icRingProtectStateChange NOTIFICATION-TYPE
    OBJECTS   { trapchassis, trapslot, trapcode, trapip, trapmoduledescription,
                trapmodetype, trapAgMdIndex, trapAgMaIndex, trapAgMepId,
                eventProtectState, trapIpString }
    STATUS      current
    DESCRIPTION
       "The module has detected a Ring Protection port state change."
    ::= { omnitronNotifications 161 }
    

-- *****************************************************************************
-- Conformance
-- *****************************************************************************

ostTrapCompliances      OBJECT IDENTIFIER ::= { ostTrapConformance 1 }
ostTrapGroups           OBJECT IDENTIFIER ::= { ostTrapConformance 2 }


-- *****************************************************************************
-- Omnitron Trap MIB Units of conformance
-- *****************************************************************************

omnitronNotificationGroup NOTIFICATION-GROUP
    NOTIFICATIONS {
        icModcoldstrt,
        icModsftreset,
        icModlinkdown,
        icModlinkup,
        icModdipsw,
        icModsoftcfg,
        icModovertemp,
        icModvoltrnge,
        icModpwrremv,
        icModpwrapply,
        icAuthfail,
        icChasnew,
        icChasgone,
        icModremove,
        icPriAct,
        icPriDis,
        icSecAct,
        icSecDis,
        icTelStart,
        icTelStop,
        icFTPStart,
        icFTPStop,
        icStnAct,
        icStnDis,
        icPwdExceeded,
        icROMchecksum,
        icROMFileType,
        icROMProgFail,
        icROMFileChecksum,
        icModuleFlashProgramComplete,
        icDyingGasp,
        icKeepAlive,
        icVlanCfgChange,
        icAISdetected,
        icPRBSdetected,
        icChassisMastershipAcquired,
        icSecureModeChange,
        icChassisMastershipRelinquished,
        icSFPDeviceInserted,
        icSFPDeviceRemoved,
        icAHEventNotificationGenerated,
        icAHEventNotificationReceived,
        icContactStatusChange,
        icAHLinkFaultReceived,
        icAHCriticalEventGenerated,
        icAHCriticalEventReceived,
        icAHRemoteDyingGasp,
        icResource,
        icLoopbackReplyReceived,
        icLoopbackReplyLost,
        icCfmFaultAlarm,
        icCfmLoopBackComplete,
        icCfmLinkTraceComplete,
        icCfmMepUp,
        icCfmMepDown,
        icCfmMepCrossConnect,
        icCfmLoop,
        icCfmConfigError,
        icCfmAllMepsUp,
        icCfmMepUnknown,
        icSfpTxLow,
        icSfpTxHigh,
        icSfpBiasLow,
        icSfpBiasHigh,
        icSfpVcc3Low,
        icSfpVcc3High,
        icSfpTempLow,
        icSfpTempHigh,
        icSfpAux2Low,
        icSfpAux2High,
        icSfpAux1Low,
        icSfpAux1High,
        icSfpRxLow,
        icSfpRxHigh,
        icSfpVcc2Low,
        icSfpVcc2High,
        icSfpVcc5Low,
        icSfpVcc5High,
        icLineChange,
        icConfigChange,
        icLoopbackActivation,
        icLoopbackDeactivation,
        icTimingError,
        icFramingOverrun,
        icDataUnderrun,
        icRemoteFound,
        icHardwareFault,
        icRemoteLost,
        icRemoteError,
        icRemoteGood,
        icExternalClockLost,
        icSerStart,
        icSerStop,
        icSFPOverPower,
        icRemoteTestActivation,
        icRemoteTestDeactivation,
        icLocalTestActivation,
        icLocalTestDeactivation,
        icAuthSshFail,
        icSshStart,
        icSshStop,
        icFileCorrupt,
        icProtectionSwitch,
        icProtectionMismatch,
        icFanNoRpm,
        icFanHighRpm,
        icFpgaFailure,
        icFanNormalRpm,
        ic1588SyncGained,
        ic1588SyncLost,
        ic1588PrimaryActive,
        ic1588PrimaryInactive,
        ic1588SecondaryActive,
        ic1588SecondaryInactive,
        icSyncEthernetSourceGained,
        icSyncEthernetSourceLost,
        icSyncEthernetHoldoverLost,
        icAisAlarm,
        icLckAlarm,
        icThresholdCrossing,
        icThresholdCrossingClear,
        icTdmClockStatusChange,
        icTdmEthernetFrameCount,
        icSfpReceiveCdrLossLock,
        icSfpTransmitCdrLossLock,
        icDpoeStageWarningAlarm,
        icDpoeStageFailAlarm,
        icSfpReceiveCdrGainedLock,
        icSfpTransmitCdrGainedLock,
        icModNormalTemp,
        icModNormalVoltage,
        icPortNormalData,
        icLinkOamRemoteLinkNormal,
        icLinkOamLocalLinkNormal,
        icSfpNormal,
        icPoEPdStatus,
        icProbePriorityChange,
        icAuthFtpFail,
        icAclDeny,

        icLinkOamDiscoveryComplete,
        icLinkOamDiscoveryLost,
        icServiceActivationTestInitiated,
        icServiceActivationTestCompleted,
        icUtilizationThresholdViolation,
        icUtilizationThresholdNormal,
        icLoopPreventionBlock,
        icLoopPreventionClear,
        icAuthTelnetFail,
        icRingProtectStateChange
    }
    STATUS       current
    DESCRIPTION
       "A collection of Omnitron notifications."
    ::= { ostTrapGroups 1 }


omnitronTrapGroup OBJECT-GROUP
    OBJECTS {
        trapchassis,
        trapslot,
        trapcode,
        trapip,
        trapmoduledescription,
        trapmodetype,
        trapAgMdIndex,
        trapAgMaIndex,
        trapAgMepId,
        trapAgErrorCode,
        trapIpString,
        
        eventNotificationType,
        eventNotificationErrors,
        eventNotificationErrorTotal,
        eventNotificationEventsTotal,
        eventThresholdIdentification,
        eventPortClockState,
        eventDpoeStageNumber,
        eventSetClear,
        eventPdStatus,
        contactClosureStatus,
        eventSrcIp,
        eventAclNumber,
        eventProbePriorityNew,
        eventProbePriorityOld,
        eventSrcIpString,
        eventProtectState
    }
    STATUS       current
    DESCRIPTION
       "A collection of Omnitron notification objects."
    ::= { ostTrapGroups 2 }


omnitronTrapObjectGroup OBJECT-GROUP
    OBJECTS {
        ostTrapCfgFilteringEnable,
        ostTrapCfgStatus,
        ostTrapCfgSeverity,
        ostTrapCfgSetClearAll,
        ostTrapCfgSeverityLevelReporting,

        ostAlarmStatusIdentifier,
        ostAlarmStatusInstance,
        ostAlarmStatusTime,
        ostAlarmStatusDescription,
        ostAlarmStatusClearAll,

        ostAlarmHistoryIdentifier,
        ostAlarmHistoryInstance,
        ostAlarmHistoryStartTime,
        ostAlarmHistoryEndTime,
        ostAlarmHistoryDescription
    }
    STATUS       current
    DESCRIPTION
       "A collection of Omnitron trap configurat objects."
    ::= { ostTrapGroups 3 }


-- *****************************************************************************
-- Omnitron Trap MIB Compliance statements
-- *****************************************************************************

ostTrapCompliance MODULE-COMPLIANCE
    STATUS       current
    DESCRIPTION
       "The compliance statement for the Omnitron Protocol MIB."
    MODULE
        MANDATORY-GROUPS {
            omnitronNotificationGroup,
            omnitronTrapGroup,
            omnitronTrapObjectGroup
        }
    ::= { ostTrapCompliances 1 }


END
